-- Copyright 1998-2024 by the American Association of State Highway and
-- Transportation Officials (AASHTO), the Institute of Transportation
-- Engineers (ITE), and the National Electrical Manufacturers Association
-- (NEMA). All intellectual property rights, including, but not limited to,
-- the rights of reproduction in whole or in part in any form, translation
-- into other languages and display are reserved by the copyright owners
-- under the laws of the United States of America, the Universal Copyright
-- Convention, the Berne Convention, and the International and Pan American
-- Copyright Conventions.
-- 
-- Joint NEMA, AASHTO, and ITE
-- NTCIP Management Information Base
-- DISTRIBUTION NOTICE
--
-- To the extent and in the limited event these materials are distributed by
-- AASHTO/ITE/NEMA in the form of a Management Information Base ("MIB"),
-- AASHTO/ITE/NEMA extends the following permissions:
--
-- You may make and distribute unlimited copies of this file, including
-- copies for commercial distribution, provided that:
--   (a) the copies are not edited from this official version and
--   (b) each copy contains this Notice
--
-- These materials are delivered "AS IS" without any warranties as to their
-- use or performance.
--
-- AASHTO/ITE/NEMA AND THEIR SUPPLIERS DO NOT WARRANT THE PERFORMANCE OR
-- RESULTS YOU MAY OBTAIN BY USING THESE MATERIALS. AASHTO/ITE/NEMA AND THEIR
-- SUPPLIERS MAKE NO WARRANTIES, EXPRESS OR IMPLIED, AS TO NONINFRINGEMENT OF
-- THIRD PARTY RIGHTS, MERCHANTABILITY, OR FITNESS FOR ANY PARTICULAR PURPOSE.
-- IN NO EVENT WILL AASHTO, ITE OR NEMA OR THEIR SUPPLIERS BE LIABLE TO YOU OR
-- ANY THIRD PARTY FOR ANY CLAIM OR FOR ANY CONSEQUENTIAL, INCIDENTAL OR
-- SPECIAL DAMAGES, INCLUDING ANY LOST PROFITS OR LOST SAVINGS, ARISING FROM
-- YOUR REPRODUCTION OR USE OF THESE MATERIALS, EVEN IF AN AASHTO, ITE, OR
-- NEMA REPRESENTATIVE HAS BEEN ADVISED OF THE POSSIBILITY OF SUCH DAMAGES.
-- Some states or jurisdictions do not allow the exclusion or limitation of
-- incidental, consequential or special damages, or the exclusion of implied
-- warranties, so the above limitations may not apply to you.
--
-- Use of these materials does not constitute an endorsement or affiliation by
-- or between AASHTO, ITE, or NEMA and you, your company, or your products and
-- services.
--
-- NTCIP is a trademark of AASHTO/ITE/NEMA.
--
-- 5.1 MIB Header
NTCIP1204-Ess DEFINITIONS ::= BEGIN

IMPORTS
MODULE-IDENTITY, OBJECT-IDENTITY, OBJECT-TYPE, 
Integer32, Unsigned32, Counter32
                                               FROM SNMPv2-SMI
                                                 -- RFC 2578  
DisplayString
                                               FROM SNMPv2-TC
                                                 -- RFC 2579
OBJECT-GROUP
                                               FROM SNMPv2-CONF
                                                 -- RFC 2580
SnmpAdminString
                                               FROM SNMP-FRAMEWORK-MIB
                                                 -- RFC 3411
PhysicalIndexOrZero
                                               FROM ENTITY-MIB
                                                 -- RFC 6933
ITSTimeStamp, ITSInteger16, ITSOerString 
                                               FROM ISO26048-1-Global-TC
devices
                                               FROM NTCIP8004-Transportation;

ess MODULE-IDENTITY
  LAST-UPDATED  "202503181524Z"
  ORGANIZATION  "NTCIP ESSS WG"
  CONTACT-INFO
   "name: NTCIP Coordinator
    email: ntcip@nema.org
    postal: National Electrical Manufacturers Association
            1300 North 17th Street, Suite 1752
            Rosslyn, Virginia 22209-3801"
  DESCRIPTION
   "<Definition> This MIB defines the environmental sensor station (ESS) objects. 
    <Object Identifier> 1.3.6.1.4.1.1206.4.2.5"
  REVISION     "202503181524Z"
  DESCRIPTION
    "<Definition> NTCIP 1204 v05 - Upgraded to SMIv2 format and incorporated objects from the ISO 26048 series into design."
  REVISION     "202204010500Z"
  DESCRIPTION
    "<Definition> NTCIP 1204 v04 - Improved 1) support for multiple sensors of the same type, 2) support for infrared sensors that collect multiple parameters from the same sensor, and 3) support for metadata. Other edits as needed."
  REVISION     "200910300500Z"
  DESCRIPTION
    "<Definition> NTCIP 1204 v03 - Added test procedures to Annex C and other edits."
  REVISION     "200507230500Z"
  DESCRIPTION
    "<Definition> NTCIP 1204 v02 - Added systems engineering content, including Section 2(Concept of Operations), Section 3 (Requirements), Section 4 (Dialogs), and Annex A (Requirements Traceability Table) along with other refinements based on lessons learned."
  REVISION     "200111230500Z"
  DESCRIPTION
    "<Definition> NTCIP 1204 v01A1 - Corrected typos and other issues in the original document."
  REVISION     "199809280500Z"
  DESCRIPTION
    "<Definition> NTCIP 1204 v01 - Initial version of NTCIP 1204."
::= { devices 5 }

essBufr OBJECT-IDENTITY
    STATUS       current
  DESCRIPTION
    "<Definition> This node contains objects that describe BUFR information based on
the BUFR Standards. 
    <Object Identifier> 1.3.6.1.4.1.1206.4.2.5.1"
::= {ess 1}

essNtcip OBJECT-IDENTITY
    STATUS       current
  DESCRIPTION
    "<Definition> This node contains objects that describe surface transportation environmental information which deviates from the BUFR Standards.
    <Object Identifier> 1.3.6.1.4.1.1206.4.2.5.2"
::= {ess 2}

-- 5.2 Identification Objects
essNtcipIdentification OBJECT-IDENTITY
    STATUS       current
  DESCRIPTION
    "<Definition> These are objects used to describe the identification of the environmental sensor station.
    <Object Identifier> 1.3.6.1.4.1.1206.4.2.5.2.1"
::= {essNtcip 1 }

-- 5.2.1 Station Category
-- This object has been deprecated.
essNtcipCategory OBJECT-TYPE
  SYNTAX       INTEGER { 
    other (1), 
    permanent (2), 
    transportable (3), 
    mobile (4) }
  MAX-ACCESS   read-only
  STATUS       deprecated
  DESCRIPTION
    "<Definition> Indicates the category of station as it relates to mobility.
    <Format>
value          description
other          of a design not listed in this standard. 
permanent      not designed to be relocated.
transportable  able to be relocated, but does not take readings while 
               moving.
mobile         capable of taking readings while moving.
    <Parameter Type> status
    <Superseded by> ISO26048-1-FieldDevice.fdMobility
    <Informative> This object was deprecated in NTCIP 1204 v05.
    <Object Identifier> 1.3.6.1.4.1.1206.4.2.5.2.1.1"
::= { essNtcipIdentification 1 }

-- 5.2.2 Site Description
-- This object has been deprecated.
essNtcipSiteDescription OBJECT-TYPE
  SYNTAX       DisplayString (SIZE (0..255))
  MAX-ACCESS   read-write
  STATUS       deprecated
  DESCRIPTION
    "<Definition> A textual description of the station's location.
    <Parameter Type> configuration
    <Supplanted by> SNMPv2-MIB.sysLocation (RFC 3418)
    <Informative> Version 02 of the standard incorrectly defined a SetConstraint of read-only, even though the object has always been defined with an access of read-write. This was corrected in version 03. This object was deprecated in NTCIP 1204 v05.
    <Object Identifier> 1.3.6.1.4.1.1206.4.2.5.2.1.2"
::= { essNtcipIdentification 2 }

-- 5.3 Data Instrumentation Objects
essBufrInstrumentation OBJECT-IDENTITY
    STATUS       current
  DESCRIPTION
    "<Definition> Objects used to describe the type of data and the type of instrumentation used to collect the data being received from the ess when the data has a BUFR equivalent. 
    <Object Identifier> 1.3.6.1.4.1.1206.4.2.5.1.2"
::= { essBufr 2 }

essNtcipInstrumentation OBJECT-IDENTITY
    STATUS       current
  DESCRIPTION
    "<Definition> Objects used to describe the type of data and the type of instrumentation used to collect the data being received from the ESS when there is not a BUFR equivalent to the data.
    <Object Identifier> 1.3.6.1.4.1.1206.4.2.5.2.15"
::= { essNtcip 15 }

-- It is also recognized that there would be a great value of an object to indicate the quality of data; however, this is a very complex topic and thus we have not determined an appropriate mechanism.

-- 5.3.1 Type of Station
essTypeofStation OBJECT-TYPE
  SYNTAX       INTEGER {
    automatic (0),
    staffed (1),
    reserved (2),
    missingValue (3) }
  MAX-ACCESS   read-only
  STATUS       current
  DESCRIPTION
    "<Definition> Integer value that indicates the type of station. If the station is a hybrid station, it should be represented with two SNMP contexts, one would report automatic and report all automatic readings while the other would report staffed and provide only the human readings.
    <Format>
value               description 
0 - automatic      the data is collected electronically/mechanically 
1 - staffed        the data is collected by humans 
2 - reserved
3 - missingValue   the type of station is unknown.
    <Parameter Type> status
    <Informative> The value of 2 has been explicitly defined as being reserved. To be defined as two stations (e.g., for a hybrid), a station needs to have two addresses and two instances of this MIB.
The syntax was changed from INTEGER (0..3) to an enumeration in version 05.
    <Object Identifier> 1.3.6.1.4.1.1206.4.2.5.1.2.1"
  REFERENCE    "WMO Binary Code Form FM 94 BUFR Table B item 0 02 001"
::= { essBufrInstrumentation 1 }

-- 5.3.2 Door Status
-- This object has been deprecated.
essDoorStatus OBJECT-TYPE
  SYNTAX       Integer32 (0..1)
  MAX-ACCESS   read-only
  STATUS       deprecated
  DESCRIPTION
    "<Definition> Indicates whether any of the doors attached to the station are open. If the value is one (1), at least one door is open; if the value is zero (0), all doors associated with the ESS are closed.
    <Parameter Type> status
    <Superseded by> ISO26048-1-Srsa.fdSrsaTypeWarning.FDO
    <Informative> This object was deprecated in v05 to migrate to a more generic SRSA design that allow reporting the status of each door associated with the ESS.
    <Object Identifier> 1.3.6.1.4.1.1206.4.2.5.2.15.1"
::= { essNtcipInstrumentation 1 }

-- 5.3.3 Battery Status
-- This object has been deprecated.
essBatteryStatus OBJECT-TYPE
  SYNTAX       Integer32 (0..101)
  UNITS        "percent"
  MAX-ACCESS   read-only
  STATUS       deprecated
  DESCRIPTION
    "<Definition> Indicates the current charge stored in the battery.
    <Format>
Values 0 to 100 indicate percent of full charge. The value 101 indicates an error in determining the percent of charge.
    <Parameter Type> status
    <Superseded by> ISO26048-1-Srsa.fdSrsaPortValue.FBC
    <Informative> This object was deprecated in v05 to migrate to a more generic SRSA design.
    <Object Identifier> 1.3.6.1.4.1.1206.4.2.5.2.15.2"
::= { essNtcipInstrumentation 2 }

-- 5.3.4 Line Volts
-- This object has been deprecated.
essLineVolts OBJECT-TYPE
  SYNTAX       Integer32 (0..255)
  UNITS        "*2 Volts Root Mean Squared (Vrms)"
  MAX-ACCESS   read-only
  STATUS       deprecated
  DESCRIPTION
    "<Definition> Indicates the voltage measured on the incoming power line for the controller. The value reported indicates one-half of the actual voltage; thus, this object indicates a value of 55 when the voltage is 110 Vrms. This object shall only be used to indicate A/C power conditions. If the line power is DC, this object shall not apply (i.e., either is not supported or has a value of 255) and the essBatteryStatus object shall indicate the status of the batteries.
    <Format>
Values 0 through 254 shall indicate valid values. The value 254 shall mean a voltage of 508 Vrms or greater. The value of 255 shall indicate an error condition or missing value.
    <Parameter Type> status
    <Superseded by> ISO26048-1-Srsa.fdSrsaPortValue.FLV
    <Informative> This object was deprecated in v05 to migrate to a more generic SRSA design.
    <Object Identifier> 1.3.6.1.4.1.1206.4.2.5.2.15.3"
::= { essNtcipInstrumentation 3 }

-- 5.3.5 Station Meta Data Block
-- This object has been deprecated.
essStationMetaDataBlock OBJECT-TYPE
  SYNTAX       ITSOerString
  MAX-ACCESS   read-only
  STATUS       deprecated
  DESCRIPTION
    "<Definition> An OER encoded string of the EssStationMetaData structure 
as defined below. This object is used for uploading configuration 
data from the ESS in a bandwidth efficient manner.

The OPTIONAL fields shall be present if the data is supported by the 
implementation and is valid. The OPTIONAL fields shall be omitted for 
any data that is invalid or not supported by the implementation.

EssStationMetaData ::= SEQUENCE {  
essNtcipCategory.0    OPTIONAL,  -- @NTCIP1204-Ess
essTypeOfStation.0    OPTIONAL,  -- @NTCIP1204-Ess
essLatitude.0         OPTIONAL,  -- @NTCIP1204-Ess
essLongitude.0        OPTIONAL,  -- @NTCIP1204-Ess
essReferenceHeight.0  OPTIONAL,  -- @NTCIP1204-Ess
essPressureHeight.0   OPTIONAL,  -- @NTCIP1204-Ess
essWindSensorHeight.0 OPTIONAL,  -- @NTCIP1204-Ess
temperatureMetaData SEQUENCE OF TemperatureMetaData  OPTIONAL,
pavementMetaData    SEQUENCE OF PavementMetaData     OPTIONAL,
subSurfaceMetaData  SEQUENCE OF SubSurfaceMetaData   OPTIONAL,
treatmentMetaData   SEQUENCE OF TreatmentMetaData    OPTIONAL
}

TemperatureMetaData ::= SEQUENCE {
essTemperatureSensorIndex.x     OPTIONAL, -- @NTCIP1204-Ess
essTemperatureSensorHeight.x    OPTIONAL  -- @NTCIP1204-Ess
}

PavementMetaData ::= SEQUENCE {
essPavementSensorIndex.x    OPTIONAL,  -- @NTCIP1204-Ess
essPavementType.x           OPTIONAL,  -- @NTCIP1204-Ess
essPavementElevation.x      OPTIONAL,  -- @NTCIP1204-Ess
essPavementExposure.x       OPTIONAL,  -- @NTCIP1204-Ess
essPavementSensorType.x     OPTIONAL   -- @NTCIP1204-Ess
}

SubSurfaceMetaData ::= SEQUENCE {
essSubSurfaceSensorIndex.x    OPTIONAL,  -- @NTCIP1204-Ess
essSubSurfaceType.x           OPTIONAL,  -- @NTCIP1204-Ess
essSubSurfaceSensorDepth.x    OPTIONAL   -- @NTCIP1204-Ess
}

TreatmentMetaData ::= SEQUENCE {
essPavementTreatmentIndex.x    OPTIONAL,  -- @NTCIP1204-Ess
essPaveTreatProductType.x      OPTIONAL,  -- @NTCIP1204-Ess
essPaveTreatProductForm.x      OPTIONAL,  -- @NTCIP1204-Ess
essPercentProductMix.x         OPTIONAL   -- @NTCIP1204-Ess 
}
    <Parameter Type> status
    <Superseded by> essStationMetaDataV3Block
    <Informative> This object was deprecated in version 03. 
    <Object Identifier> 1.3.6.1.4.1.1206.4.2.5.2.15.4"
::= { essNtcipInstrumentation 4 }

-- 5.3.6 Weather Block
-- This object has been deprecated.
essWeatherBlock OBJECT-TYPE
  SYNTAX       ITSOerString
  MAX-ACCESS   read-only
  STATUS       deprecated
  DESCRIPTION
    "<Definition> An OER encoded string of the EssWeatherData structure as 
defined in Section 4. This object is used for uploading current 
weather data from the ESS in a bandwidth efficient manner.

The OPTIONAL fields shall be present if the data is supported by the 
implementation and is valid. The OPTIONAL fields shall be omitted for
any data that is invalid or not supported by the implementation.

EssWeatherData ::= SEQUENCE {
essAtmosphericPressure.0    OPTIONAL, -- @NTCIP1204-Ess
essWindData          EssWindData         OPTIONAL,
essTemperatureData   EssTemperatureData  OPTIONAL,
essPrecipData        EssPrecipData       OPTIONAL,
essVisibilityData    EssVisibilityData   OPTIONAL
}

EssWindData ::= SEQUENCE {
essAvgWindDirection.0   OPTIONAL,  -- @NTCIP1204-Ess
essAvgWindSpeed.0       OPTIONAL,  -- @NTCIP1204-Ess
essWindSituation.0      OPTIONAL,  -- @NTCIP1204-Ess
essMaxWindGustSpeed.0   OPTIONAL,  -- @NTCIP1204-Ess
essMaxWindGustDir.0     OPTIONAL,  -- @NTCIP1204-Ess
essSpotWindDirection.0  OPTIONAL,  -- @NTCIP1204-Ess
essSpotWindSpeed.0      OPTIONAL   -- @NTCIP1204-Ess
}

EssTemperatureData ::= SEQUENCE {
essWetBulbTemp.0       OPTIONAL,  -- @NTCIP1204-Ess
essDewpointTemp.0      OPTIONAL,  -- @NTCIP1204-Ess
essMaxTemp.0           OPTIONAL,  -- @NTCIP1204-Ess
essMinTemp.0           OPTIONAL,  -- @NTCIP1204-Ess
essRelativeHumidity.0  OPTIONAL,  -- @NTCIP1204-Ess
  -- for (
--   x = 1; 
--   x < essNumTemperatureSensors.0; 
--   x++)
temperatureTable       SEQUENCE OF Temperature OPTIONAL
}

Temperature ::= SEQUENCE {
essTemperatureSensorIndex.x  OPTIONAL, -- @NTCIP1204-Ess
essAirTemperature.x          OPTIONAL  -- @NTCIP1204-Ess
}

EssPrecipData ::= SEQUENCE { 
essWaterDepth.0               OPTIONAL,  -- @NTCIP1204-Ess
essAdjacentSnowDepth.0        OPTIONAL,  -- @NTCIP1204-Ess
essRoadwaySnowDepth.0         OPTIONAL,  -- @NTCIP1204-Ess
essRoadwaySnowPackDepth.0     OPTIONAL,  -- @NTCIP1204-Ess
essPrecipYesNo.0              OPTIONAL,  -- @NTCIP1204-Ess
essPrecipRate.0               OPTIONAL,  -- @NTCIP1204-Ess
essSnowfallAccumRate.0        OPTIONAL,  -- @NTCIP1204-Ess
essPrecipSituation.0          OPTIONAL,  -- @NTCIP1204-Ess
essIceThickness.0             OPTIONAL,  -- @NTCIP1204-Ess
essPrecipitationStartTime.0   OPTIONAL,  -- @NTCIP1204-Ess
essPrecipitationEndTime.0     OPTIONAL  -- @NTCIP1204-Ess
essPrecipitationOneHour.0     OPTIONAL,  -- @NTCIP1204-Ess
essPrecipitationThreeHours.0  OPTIONAL,  -- @NTCIP1204-Ess
essPrecipitationSixHours.0    OPTIONAL,  -- @NTCIP1204-Ess
essPrecipitationTwelveHours.0 OPTIONAL,  -- @NTCIP1204-Ess
essPrecipitation24Hours.0     OPTIONAL   -- @NTCIP1204-Ess
}

EssVisibilityData ::= SEQUENCE {
essSolarRadiation.0       OPTIONAL,  -- @NTCIP1204-Ess
essTotalSun.0             OPTIONAL,  -- @NTCIP1204-Ess
essCloudSituation.0       OPTIONAL,  -- @NTCIP1204-Ess
essVisibility.0           OPTIONAL,  -- @NTCIP1204-Ess
essVisibilitySituation.0  OPTIONAL   -- @NTCIP1204-Ess
}
    <Parameter Type> status
    <Superseded by> essWeatherV3Block
    <Informative> This object was deprecated in NTCIP 1204 v03.
    <Object Identifier> 1.3.6.1.4.1.1206.4.2.5.2.15.5"
::= { essNtcipInstrumentation 5 }

-- 5.3.7 Mobile Block
-- This object has been deprecated.
essMobileBlock OBJECT-TYPE
  SYNTAX       ITSOerString
  MAX-ACCESS   read-only
  STATUS       deprecated
  DESCRIPTION
    "<Definition> An OER encoded string of the EssMobileData structure as 
defined below. This object is used for uploading current mobile 
station data from the ESS in a bandwidth efficient manner.

The OPTIONAL fields shall be present if the data is supported by the 
implementation and is valid. The OPTIONAL fields shall be omitted for
any data that is invalid or not supported by the implementation.

EssMobileData ::= SEQUENCE { 
  essLatitude.0                     OPTIONAL, -- @NTCIP1204-Ess
  essLongitude.0                    OPTIONAL, -- @NTCIP1204-Ess
  essReferenceHeight.0              OPTIONAL, -- @NTCIP1204-Ess
  essVehicleSpeed.0                 OPTIONAL, -- @NTCIP1204-Ess
  essVehicleBearing.0               OPTIONAL, -- @NTCIP1204-Ess
  essVehicleOdometer.0              OPTIONAL, -- @NTCIP1204-Ess
  essMobileFriction.0               OPTIONAL, -- @NTCIP1204-Ess
  essMobileObservationGroundState.0 OPTIONAL, -- @NTCIP1204-Ess
  essMobileObservationPavement.0    OPTIONAL, -- @NTCIP1204-Ess
  essPaveTreatmentAmount.0          OPTIONAL, -- @NTCIP1204-Ess
  essPaveTreatmentWidth.0           OPTIONAL  -- @NTCIP1204-Ess
  }
    <Parameter Type> status
    <Informative> This object was deprecated and withdrawn in version 04 as the associated requirement was deemed to be no longer necessary.
    <Object Identifier> 1.3.6.1.4.1.1206.4.2.5.2.15.6"
::= { essNtcipInstrumentation 6 }

-- 5.3.8 Station Meta Data Block Version 3
-- This object has been deprecated.
essStationMetaDataV3Block OBJECT-TYPE
  SYNTAX       ITSOerString
  MAX-ACCESS   read-only
  STATUS       deprecated
  DESCRIPTION
    "<Definition> An OER encoded string of the EssStationMetaDataV3 structure 
as defined below. This object is used for uploading configuration 
data from the ESS in a bandwidth efficient manner.

The OPTIONAL fields shall be present if the data is supported by the 
implementation and is valid. The OPTIONAL fields shall be omitted for 
any data that is invalid or not supported by the implementation.

EssStationMetaDataV3 ::= SEQUENCE {  
essNtcipCategory.0,                   OPTIONAL,  -- @NTCIP1204-Ess
essTypeOfStation.0,                   OPTIONAL,  -- @NTCIP1204-Ess
essLatitude.0,                        OPTIONAL,  -- @NTCIP1204-Ess
essLongitude.0,                       OPTIONAL,  -- @NTCIP1204-Ess
essReferenceHeight.0,                 OPTIONAL,  -- @NTCIP1204-Ess
essPressureHeight.0,                  OPTIONAL,  -- @NTCIP1204-Ess
precipitationSensorModelInformation.0 OPTIONAL -- @NTCIP1204-Ess
windMetaData.0,     SEQUENCE OF WindMetaData        OPTIONAL,  
temperatureMetaData SEQUENCE OF TemperatureMetaData OPTIONAL,
pavementMetaData    SEQUENCE OF PavementMetaData    OPTIONAL,
subSurfaceMetaData  SEQUENCE OF SubSurfaceMetaData  OPTIONAL,
treatmentMetaData   SEQUENCE OF TreatmentMetaData   OPTIONAL
}

WindMetaData ::= SEQUENCE {
windSensorIndex.x       OPTIONAL,  -- @NTCIP1204-Ess
windSensorHeight.x      OPTIONAL   -- @NTCIP1204-Ess
}

TemperatureMetaData ::= SEQUENCE {
essTemperatureSensorIndex.x    OPTIONAL,  -- @NTCIP1204-Ess
essTemperatureSensorHeight.x   OPTIONAL   -- @NTCIP1204-Ess
}

PavementMetaData ::= SEQUENCE {
essPavementSensorIndex.x,         OPTIONAL,  -- @NTCIP1204-Ess
essPavementType.x,                OPTIONAL,  -- @NTCIP1204-Ess
essPavementElevation.x            OPTIONAL,  -- @NTCIP1204-Ess
essPavementExposure.x             OPTIONAL,  -- @NTCIP1204-Ess
essPavementSensorType.x           OPTIONAL,  -- @NTCIP1204-Ess
pavementSensorModelInformation.x  OPTIONAL,  -- @NTCIP1204-Ess
pavementSensorTemperatureDepth.x  OPTIONAL   -- @NTCIP1204-Ess
}

SubSurfaceMetaData ::= SEQUENCE {
essSubSurfaceSensorIndex.x  OPTIONAL,  -- @NTCIP1204-Ess
essSubSurfaceType.x         OPTIONAL,  -- @NTCIP1204-Ess
essSubSurfaceSensorDepth.x  OPTIONAL   -- @NTCIP1204-Ess
}

TreatmentMetaData ::= SEQUENCE {
essPavementTreatmentIndex.x  OPTIONAL,  -- @NTCIP1204-Ess
essPaveTreatProductType.x    OPTIONAL,  -- @NTCIP1204-Ess
essPaveTreatProductForm.x    OPTIONAL,  -- @NTCIP1204-Ess
essPercentProductMix.x       OPTIONAL   -- @NTCIP1204-Ess 
}
    <Parameter Type> status
    <Informative> This object was deprecated and withdrawn in NTCIP 1204 v04 as the associated requirement was deemed to be no longer necessary.
    <Object Identifier> 1.3.6.1.4.1.1206.4.2.5.2.15.7"
::= { essNtcipInstrumentation 7 }

-- 5.3.9 Weather Block Version 3
-- This object has been deprecated.
essWeatherV3Block OBJECT-TYPE
  SYNTAX       ITSOerString
  MAX-ACCESS   read-only
  STATUS       deprecated
  DESCRIPTION
    "<Definition> An OER encoded string of the EssWeatherDataV3 structure as 
defined below. This object is used for uploading current weather data 
from the ESS in a bandwidth efficient manner.

The OPTIONAL fields shall be present if the data is supported by the 
implementation and is valid. The OPTIONAL fields shall be omitted for 
any data that is invalid or not supported by the implementation.

EssWeatherDataV3 ::= SEQUENCE {
essAtmosphericPressure.0  OPTIONAL,  -- @NTCIP1204-Ess
essWindData               SEQUENCE OF EssWindDataV3  OPTIONAL,
essTemperatureData        EssTemperatureData         OPTIONAL,
essPrecipData             EssPrecipDataV3            OPTIONAL,
essVisibilityData         EssVisibilityDataV3        OPTIONAL, 
essRadiationData          EssRadiationData           OPTIONAL
}

EssWindDataV3 ::= SEQUENCE {
windSensorIndex.x         OPTIONAL,  -- @NTCIP1204-Ess
windSensorAvgSpeed.x      OPTIONAL,  -- @NTCIP1204-Ess
windSensorAvgDirection.x  OPTIONAL,  -- @NTCIP1204-Ess
windSensorSpotSpeed.x     OPTIONAL,  -- @NTCIP1204-Ess
windSensorSpotDirection.x OPTIONAL,  -- @NTCIP1204-Ess
windSensorGustSpeed.x     OPTIONAL,  -- @NTCIP1204-Ess
windSensorGustDirection.x OPTIONAL,  -- @NTCIP1204-Ess
windSensorSituation.x     OPTIONAL,  -- @NTCIP1204-Ess
}

EssTemperatureData ::= SEQUENCE {
essWetBulbTemp.0          OPTIONAL,  -- @NTCIP1204-Ess
essDewpointTemp.0         OPTIONAL,  -- @NTCIP1204-Ess
essMaxTemp.0              OPTIONAL,  -- @NTCIP1204-Ess
essMinTemp.0              OPTIONAL,  -- @NTCIP1204-Ess
essRelativeHumidity.0     OPTIONAL,  -- @NTCIP1204-Ess
  -- for (
  --   x = 1; 
  --   x < essNumTemperatureSensors.0; 
  --   x++)
temperatureTable          SEQUENCE OF Temperature  OPTIONAL, 
}

Temperature ::= SEQUENCE {
essTemperatureSensorIndex.x  OPTIONAL,  -- @NTCIP1204-Ess
essAirTemperature.x          OPTIONAL,  -- @NTCIP1204-Ess
}

EssPrecipDataV3 ::= SEQUENCE { 
waterLevelSensorTable       SEQUENCE OF WaterLevel  OPTIONAL,
essAdjacentSnowDepth.0      OPTIONAL,  -- @NTCIP1204-Ess
essRoadwaySnowDepth.0       OPTIONAL,  -- @NTCIP1204-Ess
essRoadwaySnowPackDepth.0   OPTIONAL,  -- @NTCIP1204-Ess
essPrecipYesNo.0            OPTIONAL,  -- @NTCIP1204-Ess
essPrecipRate.0             OPTIONAL,  -- @NTCIP1204-Ess
essSnowfallAccumRate.0      OPTIONAL,  -- @NTCIP1204-Ess
essPrecipSituation.0        OPTIONAL,  -- @NTCIP1204-Ess
essIceThickness.0           OPTIONAL,  -- @NTCIP1204-Ess
essPrecipitationStartTime.0 OPTIONAL,  -- @NTCIP1204-Ess
essPrecipitationEndTime.0   OPTIONAL,  -- @NTCIP1204-Ess
}

WaterLevel ::= SEQUENCE {
waterLevelSensorIndex.x      OPTIONAL,  -- @NTCIP1204-Ess
waterLevelSensorReading.x    OPTIONAL,  -- @NTCIP1204-Ess
}

EssVisibilityDataV3 ::= SEQUENCE {
essVisibility.0             OPTIONAL,  -- @NTCIP1204-Ess
essVisibilitySituation.0    OPTIONAL,  -- @NTCIP1204-Ess
}

EssRadiationData ::= SEQUENCE {
essTotalSun.0                           OPTIONAL,  -- @NTCIP1204-Ess
essInstantaneousTerrestrialRadiation.0  OPTIONAL,  -- @NTCIP1204-Ess
essInstantaneousSolarRadiation.0        OPTIONAL,  -- @NTCIP1204-Ess
essTotalRadiation.0                     OPTIONAL,  -- @NTCIP1204-Ess
essTotalRadiationPeriod.0               OPTIONAL,  -- @NTCIP1204-Ess
essCloudSituation.0                     OPTIONAL,  -- @NTCIP1204-Ess
}
    <Parameter Type> status
    <Informative> This object was deprecated and withdrawn in NTCIP 1204 v04 as the associated requirement was deemed to be no longer necessary.
    <Object Identifier> 1.3.6.1.4.1.1206.4.2.5.2.15.8"
::= { essNtcipInstrumentation 8 }

-- 5.3.10 ESS Status
-- This object has been deprecated.
essStatus OBJECT-TYPE
  SYNTAX       Integer32 (0..3)
  MAX-ACCESS   read-only
  STATUS       deprecated
  DESCRIPTION
    "<Definition> Integer value that indicates whether an error condition has been detected in the ESS hardware or software. 
    <Format>
value                description 
0 - noError         no error is reported 
1 - watchdogFailure     the watchdog has failed 
2 - powerError  irregular occurrence detected with primary power source
3 - sensorFailure  condition detected preventing proper reporting or a 
    sensor value is deemed invalid or suspect
    <Parameter Type> status
    <Superseded by> ISO26048-1-Controller.fdControllerStatus
    <Informative> The object was deprecated in NTCIP 1204 v05.
    <Object Identifier> 1.3.6.1.4.1.1206.4.2.5.2.15.9"
::= { essNtcipInstrumentation 9 }

-- 5.4 Location Objects
essNtcipLocation OBJECT-IDENTITY
    STATUS       current
  DESCRIPTION
    "<Definition> Contains objects used to describe the location of the ESS that is
transmitting the collected data.
    <Object Identifier> 1.3.6.1.4.1.1206.4.2.5.2.2"
::= {essNtcip 2 }

-- 5.4.1 Latitude
-- This object has been deprecated.
essLatitude OBJECT-TYPE
  SYNTAX       Integer32 (-90000000..90000001)
  UNITS        "microdegrees of latitude"
  MAX-ACCESS   read-only
  STATUS       deprecated
  DESCRIPTION
    "<Definition> The latitude in 10^-6 degrees of the ESS station, per WGS-84 datum.
    <Format>
The essLatitude at the North Pole is 90,000,000. The essLatitude at the South Pole is -90,000,000. The value 90,000,001 shall indicate a missing value.
    <Parameter Type> status
    <Superseded by> ISO26048-1-FieldDevice.fdConfiguredLatitude
    <Informative> This object was deprecated in NTCIP 1204 v05 to use the more generic object and to be consistent with preferred units used in ITS (i.e., 10^-7 degrees). 
    <Object Identifier> 1.3.6.1.4.1.1206.4.2.5.2.2.1"
  REFERENCE    "Resolution based on on-going location referencing activities; the WMO Binary Code Form FM 94 BUFR Table B item 0 05 001 can be obtained by dividing this value by 10."
::= { essNtcipLocation 1 }

-- 5.4.2 Longitude
-- This object has been deprecated.
essLongitude OBJECT-TYPE
  SYNTAX       Integer32 (-180000000..180000001)
  UNITS        "microdegrees of longitude"
  MAX-ACCESS   read-only
  STATUS       deprecated
  DESCRIPTION
    "<Definition> The east longitude in 10^-6 degrees from the Prime Meridian of the ESS location. 
    <Format>
The essLongitude of 180 degrees West shall be -180,000,000. The essLongitude of 180 degrees East shall be 180,000,000. The value 180,000,001 shall indicate a missing value.
    <Parameter Type> status
    <Superseded by> ISO26048-1-FieldDevice.fdConfiguredLongitude 
    <Informative> This object was deprecated in NTCIP 1204 v05 to use the more generic object and to be consistent with preferred units used in ITS (i.e., 10^-7 degrees). 
    <Object Identifier> 1.3.6.1.4.1.1206.4.2.5.2.2.2"
  REFERENCE    "Resolution based on on-going location referencing activities; the WMO Binary Code Form FM 94 BUFR Table B item 0 06 001 can be obtained by dividing this value by 10."
::= { essNtcipLocation 2 }

-- 5.4.3 Vehicle Speed
-- This object has been deprecated.
essVehicleSpeed OBJECT-TYPE
  SYNTAX       Integer32 (0..255)
  UNITS        "kilometers per hour"
  MAX-ACCESS   read-only
  STATUS       deprecated
  DESCRIPTION
    "<Definition> Indicates the current speed being reported by the vehicle in kilometers per hour. 
    <Format>
The value 255 shall indicate an error condition or missing value.
    <Parameter Type> status
    <Superseded by> ISO26048-1-FieldDevice.fdSpeed
    <Informative> This object was deprecated in NTCIP 1204 v05. 
    <Object Identifier> 1.3.6.1.4.1.1206.4.2.5.2.2.3"
::= { essNtcipLocation 3 }

-- 5.4.4 Vehicle Bearing
-- This object has been deprecated.
essVehicleBearing OBJECT-TYPE
  SYNTAX       Integer32 (0..361)
  UNITS        "compass degrees"
  MAX-ACCESS   read-only
  STATUS       deprecated
  DESCRIPTION
    "<Definition> Indicates the current bearing of the vehicle in degrees, measured clockwise from True North.
    <Format>
The value 0 shall indicate that the vehicle is stopped. The value 361 shall indicate an error condition or missing value.
    <Parameter Type> status
    <Superseded by> ISO26048-1-FieldDevice.fdBearing
    <Informative> This object was deprecated in NTCIP 1204 v05. 
    <Object Identifier> 1.3.6.1.4.1.1206.4.2.5.2.2.4"
::= { essNtcipLocation 4 }

-- 5.4.5 Odometer
-- This object has been deprecated.
essOdometer OBJECT-TYPE
  SYNTAX       Unsigned32
  UNITS        "meters"
  MAX-ACCESS   read-only
  STATUS       deprecated
  DESCRIPTION
    "<Definition> Indicates the distance traveled, in meters, by the vehicle from a reference point. Could be a vehicle odometer reading or a calculation from the vehicle's GPS.
    <Parameter Type> status
    <Superseded by> ISO26048-1-FieldDevice.fdOdometer
    <Informative> This object was deprecated in NTCIP 1204 v05. 
    <Object Identifier> 1.3.6.1.4.1.1206.4.2.5.2.2.5"
::= { essNtcipLocation 5 }

-- 5.5 Station Elevation Objects
-- This object has been deprecated.
essNtcipHeight OBJECT-IDENTITY
    STATUS       deprecated
  DESCRIPTION
    "<Definition> Objects used to describe the elevation at the ESS that is transmitting 
the collected data.
    <Object Identifier> 1.3.6.1.4.1.1206.4.2.5.2.3"
::= {essNtcip 3 }

-- This object has been deprecated.
essBufrLocationVertical OBJECT-IDENTITY
    STATUS       deprecated
  DESCRIPTION
    "<Definition> Objects used to describe the atmospheric pressure at the ESS.
    <Object Identifier> 1.3.6.1.4.1.1206.4.2.5.1.7"
::= {essBufr 7 }

essNtcipPressure OBJECT-IDENTITY
    STATUS       current
  DESCRIPTION
    "<Definition> Objects used to describe the atmospheric pressure reported by each ESS pressure sensor.
    <Object Identifier> 1.3.6.1.4.1.1206.4.2.5.2.16"
::= {essNtcip 16 }

-- 5.5.1 Reference Height
-- This object has been deprecated.
essReferenceHeight OBJECT-TYPE
  SYNTAX       Integer32 (-400..8001)
  UNITS        "meters"
  MAX-ACCESS   read-only
  STATUS       deprecated
  DESCRIPTION
    "<Definition> The reference elevation of the ESS in meters above mean sea level. For a permanent station, this height shall be measured to the base of the structure; for transportable stations, this height shall be measured to the ground surface upon which the station resides; and for mobile, this height shall be measured to the surface under the vehicle. 
    <Format>
The value of 8001 shall indicate a missing value.
    <Parameter Type> status
    <Superseded by> ISO26048-1-FieldDevice.fdConfiguredElevation
    <Informative> This object was deprecated in version 05. 
    <Object Identifier> 1.3.6.1.4.1.1206.4.2.5.2.3.1"
  REFERENCE    "Resolution based on WMO Binary Code Form FM 94 BUFR Table B item 0 07 001."
::= { essNtcipHeight 1 }

-- 5.5.2 Pressure Height
-- This object has been deprecated.
essPressureHeight OBJECT-TYPE
  SYNTAX       Integer32 (-1000..1001)
  UNITS        "meters"
  MAX-ACCESS   read-only
  STATUS       deprecated
  DESCRIPTION
    "<Definition> The height of the pressure sensor with respect to the essReferenceHeight in meters. 
    <Format>
The value of 1001 shall indicate a missing value.
    <Parameter Type> status
    <Superseded by> essPressureSensorHeight.1
    <Informative> This object was deprecated in version 04. 
    <Object Identifier> 1.3.6.1.4.1.1206.4.2.5.2.3.2"
  REFERENCE    "essReferenceHeight plus this value equals the WMO Binary Code Form FM 94 BUFR Table B item 0 07 001."
::= { essNtcipHeight 2 }

-- 5.5.3 Wind Sensor Height
-- This object has been deprecated.
essWindSensorHeight OBJECT-TYPE
  SYNTAX       Integer32 (-1000..1001)
  UNITS        "meters"
  MAX-ACCESS   read-only
  STATUS       deprecated
  DESCRIPTION
    "<Definition> The height of the primary wind sensor with respect to the essReferenceHeight in meters.
    <Format>
The value of 1001 shall indicate a missing value.
    <Parameter Type> status
    <Superseded by> windSensorHeight.1
    <Informative> This object was deprecated in version 02. 
    <Object Identifier> 1.3.6.1.4.1.1206.4.2.5.2.3.3"
::= { essNtcipHeight 3 }

-- 5.5.4 Atmospheric Pressure
-- This object has been deprecated.
essAtmosphericPressure OBJECT-TYPE
  SYNTAX       Integer32 (0..65535)
  UNITS        "decapascal"
  MAX-ACCESS   read-only
  STATUS       deprecated
  DESCRIPTION
    "<Definition> The force per unit area exerted by the atmosphere in 1/10ths of millibars, a.k.a. tenths of hectoPascals. 
    <Format>
A value of 65535 shall indicate an error condition or missing value.
    <Parameter Type> status
    <Superseded by> essPressureSensorAtmosphericPressure.1
    <Informative> This object was deprecated in version 04. 
    <Object Identifier> 1.3.6.1.4.1.1206.4.2.5.1.7.4"
  REFERENCE    "WMO Binary Code Form FM 94 BUFR Table B item 0 07 004."
::= { essBufrLocationVertical 4 }

-- 5.5.5 Number of Pressure Sensors
essNumPressureSensors OBJECT-TYPE
  SYNTAX       Integer32 (0..255)
  UNITS        "sensors"
  MAX-ACCESS   read-only
  STATUS       current
  DESCRIPTION
    "<Definition> Indicates the number of entries in the pressure sensor table.
    <Parameter Type> status
    <Informative> This value may automatically change upon connecting or disconnecting a sensor; however, the table is still defined as a static table since the creation/deletion of rows is not managed through SNMP logic.
    <Object Identifier> 1.3.6.1.4.1.1206.4.2.5.2.16.1"
::= { essNtcipPressure 1 }

-- 5.5.6 Pressure Sensor Table
essPressureSensorTable OBJECT-TYPE
  SYNTAX       SEQUENCE OF EssPressureSensorEntry
  MAX-ACCESS   not-accessible
  STATUS       current
  DESCRIPTION
    "<Definition> Table containing the pressure sensor data.
    <Object Identifier> 1.3.6.1.4.1.1206.4.2.5.2.16.2"
::= { essNtcipPressure 2 }

-- 5.5.7 Pressure Sensor
essPressureSensorEntry OBJECT-TYPE
  SYNTAX       EssPressureSensorEntry
  MAX-ACCESS   not-accessible
  STATUS       current
  DESCRIPTION
    "<Definition> A pressure sensor is a sensor that reports the atmospheric pressure. It can be described through a number of attributes as indicated by the following subclauses."
  INDEX { essPressureSensorIndex }
::= { essPressureSensorTable 1 }

EssPressureSensorEntry ::= SEQUENCE {
  essPressureSensorIndex                Integer32,
  essPressureSensorHeight               Integer32,
  essPressureSensorLatitude             Integer32,
  essPressureSensorLongitude            Integer32,
  essPressureSensorLocation             SnmpAdminString,
  essPressureSensorModelInformation     Integer32,
  -- SENSOR READINGS
  essPressureSensorAtmosphericPressure  Integer32,
  essPressureSensorXOffset              ITSInteger16,
  essPressureSensorYOffset              ITSInteger16,
  essPressureSensorZOffset              ITSInteger16,
  essPressureSensorEntityID             PhysicalIndexOrZero}

-- 5.5.7.1 Pressure Sensor Index
essPressureSensorIndex OBJECT-TYPE
  SYNTAX       Integer32 (1..255)
  MAX-ACCESS   read-only
  STATUS       current
  DESCRIPTION
    "<Definition> Enumerated list of row entries that provide atmospheric pressure sensor data.
    <Parameter Type> status
    <Object Identifier> 1.3.6.1.4.1.1206.4.2.5.2.16.2.1.1"
::= { essPressureSensorEntry 1 }

-- 5.5.7.2 Pressure Sensor Height
-- This object has been deprecated.
essPressureSensorHeight OBJECT-TYPE
  SYNTAX       Integer32 (-1000..1001)
  UNITS        "meters"
  MAX-ACCESS   read-write
  STATUS       deprecated
  DESCRIPTION
    "<Definition> The height of the pressure sensor with respect to the essReferenceHeight in meters.
    <Format>
The value of 1001 shall indicate a missing value.
    <Parameter Type> configuration
    <Superseded by> essPressureSensorZOffset
    <Informative> This object was deprecated in version 05. 
    <Object Identifier> 1.3.6.1.4.1.1206.4.2.5.2.16.2.1.2"
  REFERENCE    "essReferenceHeight plus this value equals the WMO Binary Code Form FM 94 BUFR Table B item 0 07 001."
::= { essPressureSensorEntry 2 }

-- 5.5.7.3 Pressure Sensor Latitude
-- This object has been deprecated.
essPressureSensorLatitude OBJECT-TYPE
  SYNTAX       Integer32 (-90000000..90000001)
  UNITS        "microdegrees of latitude"
  MAX-ACCESS   read-write
  STATUS       deprecated
  DESCRIPTION
    "<Definition> The latitude in 10^-6 degrees of the ESS pressure sensor, per WGS-84 datum.
    <Format>
The essPressureLatitude at the North Pole is 90,000,000. The essPressureLatitude at the South Pole is -90,000,000. The value 90,000,001 shall indicate a missing value.
    <Parameter Type> configuration
    <Superseded by> essPressureSensorYOffset
    <Informative> This object was deprecated in version 05. 
    <Object Identifier> 1.3.6.1.4.1.1206.4.2.5.2.16.2.1.3"
  REFERENCE    "Resolution based on on-going location referencing activities; the WMO Binary Code Form FM 94 BUFR Table B item 0 05 001 can be obtained by dividing this value by 10."
::= { essPressureSensorEntry 3 }

-- 5.5.7.4 Pressure Sensor Longitude
-- This object has been deprecated.
essPressureSensorLongitude OBJECT-TYPE
  SYNTAX       Integer32 (-180000000..180000001)
  UNITS        "microdegrees of longitude"
  MAX-ACCESS   read-write
  STATUS       deprecated
  DESCRIPTION
    "<Definition> The east longitude in 10^-6 degrees from the Prime Meridian of the ESS pressure sensor location.
    <Format>
The essPressureLongitude of 180 degrees West shall be -180,000,000. The essPressureLongitude of 180 degrees East shall be 180,000,000. The value 180,000,001 shall indicate a missing value.
    <Parameter Type> configuration
    <Superseded by> essPressureSensorXOffset
    <Informative> This object was deprecated in version 05. 
    <Object Identifier> 1.3.6.1.4.1.1206.4.2.5.2.16.2.1.4"
  REFERENCE    "Resolution based on on-going location referencing activities; the WMO Binary Code Form FM 94 BUFR Table B item 0 06 001 can be obtained by dividing this value by 10."
::= { essPressureSensorEntry 4 }

-- 5.5.7.5 Pressure Sensor Location
essPressureSensorLocation OBJECT-TYPE
  SYNTAX       SnmpAdminString
  MAX-ACCESS   read-write
  STATUS       current
  DESCRIPTION
    "<Definition> A textual string indicating the location of the pressure sensor.
    <Parameter Type> configuration
    <Informative> Implementations are only required to support the NVT-ASCII character set but may support additional UTF-8 characters.
    <Object Identifier> 1.3.6.1.4.1.1206.4.2.5.2.16.2.1.5"
::= { essPressureSensorEntry 5 }

-- 5.5.7.6 Pressure Sensor Model Information
-- This object has been deprecated.
essPressureSensorModelInformation OBJECT-TYPE
  SYNTAX       Integer32 (0..255)
  MAX-ACCESS   read-write
  STATUS       deprecated
  DESCRIPTION
    "<Definition> Indicates the row in the Module Table (See NTCIP 1201) that contains information about the make, model, and version number of the sensor associated with this row of the Pressure Sensor Table.
    <Format>
The value of zero indicates that this information is not available.
    <Parameter Type> configuration
    <Supplanted by> essPressureSensorEntityID
    <Informative> This object was deprecated in version 05.
    <Object Identifier> 1.3.6.1.4.1.1206.4.2.5.2.16.2.1.6"
::= { essPressureSensorEntry 6 }

-- 5.5.7.7 Pressure Sensor Atmospheric Pressure
essPressureSensorAtmosphericPressure OBJECT-TYPE
  SYNTAX       Integer32 (0..65535)
  UNITS        "decapascal"
  MAX-ACCESS   read-only
  STATUS       current
  DESCRIPTION
    "<Definition> The force per unit area exerted by the atmosphere in 1/10ths of millibars, a.k.a. tenths of hectoPascals.
    <Format>
A value of 65535 shall indicate an error condition or missing value.
    <Parameter Type> status
    <Object Identifier> 1.3.6.1.4.1.1206.4.2.5.2.16.2.1.7"
  REFERENCE    "WMO Binary Code Form FM 94 BUFR Table B item 0 07 004."
::= { essPressureSensorEntry 7 }

-- 5.5.7.8 Pressure Sensor X Offset
essPressureSensorXOffset OBJECT-TYPE
  SYNTAX       ITSInteger16
  UNITS        "centimeters"
  MAX-ACCESS   read-write
  STATUS       current
  DESCRIPTION
    "<Definition> The X offset of the pressure sensor from the field device's reference location as defined by fdConfiguredLatitude and fdConfiguredLongitude. 
    <Format>
For stationary devices, the X offset shall indicate the eastward (positive) or westward (negative) distance from the reference location. For transportable and mobile devices, the X offset shall indicate distances to the starboard side (positive) or port side (negative) of the reference location on the vehicle.
    <Parameter Type> configuration
    <Object Identifier> 1.3.6.1.4.1.1206.4.2.5.2.16.2.1.8"
::= { essPressureSensorEntry 8 }

-- 5.5.7.9 Pressure Sensor Y Offset
essPressureSensorYOffset OBJECT-TYPE
  SYNTAX       ITSInteger16
  UNITS        "centimeters"
  MAX-ACCESS   read-write
  STATUS       current
  DESCRIPTION
    "<Definition> The Y offset of the pressure sensor from the field device's reference location as defined by fdConfiguredLatitude and fdConfiguredLongitude. 
    <Format>
For stationary devices, the Y offset shall indicate the northward (positive) or southward (negative) distance from the reference location. For transportable and mobile devices, the Y offset shall indicate distances to the fore (positive) or aft (negative) of the reference location on the vehicle.
    <Parameter Type> configuration
    <Object Identifier> 1.3.6.1.4.1.1206.4.2.5.2.16.2.1.9"
::= { essPressureSensorEntry 9 }

-- 5.5.7.10 Pressure Sensor Z Offset
essPressureSensorZOffset OBJECT-TYPE
  SYNTAX       ITSInteger16
  UNITS        "centimeters"
  MAX-ACCESS   read-write
  STATUS       current
  DESCRIPTION
    "<Definition> The offset elevation of the pressure sensor from the fdConfiguredElevation in centimeters.
    <Format>
Upward offsets shall be positive and downward offsets shall be negative. 
    <Parameter Type> configuration
    <Object Identifier> 1.3.6.1.4.1.1206.4.2.5.2.16.2.1.10"
::= { essPressureSensorEntry 10 }

-- 5.5.7.11 Pressure Sensor Entity ID
essPressureSensorEntityID OBJECT-TYPE
  SYNTAX       PhysicalIndexOrZero
  MAX-ACCESS   read-only
  STATUS       current
  DESCRIPTION
    "<Definition> Indicates the row in the entPhysicalTable (See RFC 4133) that contains information about the sensor, such as the manufacturer, model, and hardware and software revision identifiers. 
    <Format>
The value of zero indicates that this information is not available.
    <Parameter Type> status
    <Informative> The mechanism used to configure this value when adding or modifying a sensor is not defined by this document and is considered manufacturer-specific.
    <Object Identifier> 1.3.6.1.4.1.1206.4.2.5.2.16.2.1.11"
::= { essPressureSensorEntry 11 }

-- 5.6 Wind Data Section
essBufrWind OBJECT-IDENTITY
    STATUS       current
  DESCRIPTION
    "<Definition> Objects used to describe the wind data that is collected at the ESS in a 
format that is consistent with BUFR.
    <Object Identifier> 1.3.6.1.4.1.1206.4.2.5.1.11"
::= {essBufr 11 }

essNtcipWind OBJECT-IDENTITY
    STATUS       current
  DESCRIPTION
    "<Definition>  Objects used to describe the wind data that is collected at the ESS in a 
format that is not defined by BUFR.
    <Object Identifier> 1.3.6.1.4.1.1206.4.2.5.2.4"
::= {essNtcip 4 }

-- 5.6.1 Average Wind Direction
-- This object has been deprecated.
essAvgWindDirection OBJECT-TYPE
  SYNTAX       Integer32 (0..361)
  UNITS        "compass degrees"
  MAX-ACCESS   read-only
  STATUS       deprecated
  DESCRIPTION
    "<Definition> A two-minute average of the direction from which the wind is blowing measured clockwise in degrees from true North and measured at a height as indicated by essWindSensorHeight. A value of 361 shall indicate an error condition or missing value.
    <Parameter Type> status
    <Superseded by> windSensorAvgDirection.1
    <Informative> This object was deprecated in version 02. 
    <Object Identifier> 1.3.6.1.4.1.1206.4.2.5.1.11.1"
  REFERENCE    "WMO Code Form FM 94 BUFR Table B item 0 11 001."
::= { essBufrWind 1 }

-- 5.6.2 Average Wind Speed
-- This object has been deprecated.
essAvgWindSpeed OBJECT-TYPE
  SYNTAX       Integer32 (0..65535)
  UNITS        "tenths of meters per second"
  MAX-ACCESS   read-only
  STATUS       deprecated
  DESCRIPTION
    "<Definition> A two-minute average of the wind speed in tenths of meters per second as measured by the primary wind sensor. 
    <Format>
The value of 65535 shall indicate an error condition or missing value.
    <Parameter Type> status
    <Superseded by> windSensorAvgSpeed.1
    <Informative> This object was deprecated in version 02. 
    <Object Identifier> 1.3.6.1.4.1.1206.4.2.5.1.11.2"
  REFERENCE    "WMO Binary Code Form FM 94 BUFR Table B item 0 11 002."
::= { essBufrWind 2 }

-- 5.6.3 Spot Wind Direction
-- This object has been deprecated.
essSpotWindDirection OBJECT-TYPE
  SYNTAX       Integer32 (0..361)
  UNITS        "compass degrees"
  MAX-ACCESS   read-only
  STATUS       deprecated
  DESCRIPTION
    "<Definition> The direction from which the wind is blowing measured in degrees clockwise from true North and measured at a height as indicated by essWindSensorHeight. A value of 361 shall indicate an error condition or missing value. For mobile platforms, the wind direction shall be corrected for vehicle movement.
    <Parameter Type> status
    <Superseded by> windSensorSpotDirection.1
    <Informative> This object was deprecated in version 02. 
    <Object Identifier> 1.3.6.1.4.1.1206.4.2.5.2.4.1"
::= { essNtcipWind 1 }

-- 5.6.4 Spot Wind Speed
-- This object has been deprecated.
essSpotWindSpeed OBJECT-TYPE
  SYNTAX       Integer32 (0..65535)
  UNITS        "tenths of meters per second"
  MAX-ACCESS   read-only
  STATUS       deprecated
  DESCRIPTION
    "<Definition> The wind speed in tenths of meters per second measured by the primary wind sensor. For mobile platforms, the wind speed shall be corrected for vehicle movement.
    <Format>
The value of 65535 shall indicate an error condition or missing value.
    <Parameter Type> status
    <Superseded by> windSensorSpotSpeed.1
    <Informative> This object was deprecated in version 02. 
    <Object Identifier> 1.3.6.1.4.1.1206.4.2.5.2.4.1"
::= { essNtcipWind 2 }

-- 5.6.5 Wind Situation
essWindSituation OBJECT-TYPE
  SYNTAX       INTEGER {
    other (1),
    unknown (2),
    calm (3),
    lightBreeze (4),
    moderateBreeze (5),
    strongBreeze (6),
    gale (7),
    moderateGale (8),
    strongGale (9),
    stormWinds (10),
    hurricaneForceWinds (11),
    gustyWinds (12) }
  MAX-ACCESS   read-only
  STATUS       current
  DESCRIPTION
    "<Definition> Describes the weather and travel situation in terms of wind from staffed stations only. Specific ranges for these values are defined in the Glossary of Meteorology.
    <Format>
Range               Meaning 
other               not defined within this standard, see manufacturers 
                    documentation 
unknown             Unknown conditions 
calm                Calm 
lightBreeze         Light breeze 
moderateBreeze      Moderate breeze 
strongBreeze        Strong breeze 
gale                Gale 
moderateGale        Moderate gale 
strongGale          Strong gale 
stormWinds          Storm winds 
hurricaneForceWinds Hurricane force winds 
gustyWinds          defined by a peak and a lull of greater than 46.3 
                    tenths of meters per second within a 2 minute period.
    <Parameter Type> status
    <Superseded by> windSensorSituation.1
    <Informative> This object was deprecated in version 02 and migrated to the wind sensor table. It was reinstated in v05 specifically for staffed stations.
    <Object Identifier> 1.3.6.1.4.1.1206.4.2.5.2.4.3"
::= { essNtcipWind 3 }

-- 5.6.6 Wind Gust Speed
-- This object has been deprecated.
essMaxWindGustSpeed OBJECT-TYPE
  SYNTAX       Integer32 (0..65535)
  UNITS        "tenths of meters per second"
  MAX-ACCESS   read-only
  STATUS       deprecated
  DESCRIPTION
    "<Definition> The maximum wind gust recorded by the primary wind sensor during the 10 minutes preceding the observation measured in tenths of meters per second. 
    <Format>
The value 65535 shall indicate an error condition or missing value.
    <Parameter Type> status
    <Superseded by> windSensorGustSpeed.1
    <Informative> This object was deprecated in version 02. 
    <Object Identifier> 1.3.6.1.4.1.1206.4.2.5.1.11.41"
  REFERENCE    "WMO Code Form FM 94 BUFR Table B item 0 11 041."
::= { essBufrWind 41 }

-- 5.6.7 Wind Gust Direction
-- This object has been deprecated.
essMaxWindGustDir OBJECT-TYPE
  SYNTAX       Integer32 (0..361)
  UNITS        "compass degrees"
  MAX-ACCESS   read-only
  STATUS       deprecated
  DESCRIPTION
    "<Definition> The direction of the maximum wind gust recorded during the 10 minutes preceding the observation at a height as indicated by essWindSensorHeight; measured in degrees clockwise from true North. The value 361 shall indicate an error condition or missing value.
    <Parameter Type> status
    <Superseded by> windSensorGustDirection.1
    <Informative> This object was deprecated in version 02. 
    <Object Identifier> 1.3.6.1.4.1.1206.4.2.5.1.11.43"
  REFERENCE    "WMO Code Form FM 94 BUFR Table B item 0 11 043."
::= { essBufrWind 43 }

-- 5.6.8 Number of Wind Sensors
windSensorTableNumSensors OBJECT-TYPE
  SYNTAX       Integer32 (0..255)
  UNITS        "sensors"
  MAX-ACCESS   read-only
  STATUS       current
  DESCRIPTION
    "<Definition> Indicates the number of entries in the wind sensor table.
    <Parameter Type> status
    <Informative> This value may automatically change upon connecting or disconnecting a sensor; however, the table is still defined as a static table since the creation/deletion of rows is not managed through SNMP logic.
    <Object Identifier> 1.3.6.1.4.1.1206.4.2.5.2.4.7"
::= { essNtcipWind 7 }

-- 5.6.9 Wind Sensor Table
windSensorTable OBJECT-TYPE
  SYNTAX       SEQUENCE OF WindSensorEntry
  MAX-ACCESS   not-accessible
  STATUS       current
  DESCRIPTION
    "<Definition> Table containing the wind sensor data fields.
    <Object Identifier> 1.3.6.1.4.1.1206.4.2.5.2.4.8"
::= { essNtcipWind 8 }

-- 5.6.10 Wind Sensor
windSensorEntry OBJECT-TYPE
  SYNTAX       WindSensorEntry
  MAX-ACCESS   not-accessible
  STATUS       current
  DESCRIPTION
    "<Definition> Parameters for specific wind sensor data fields."
  INDEX { windSensorIndex }
::= { windSensorTable 1 }

WindSensorEntry ::= SEQUENCE {
  windSensorIndex             Integer32,
  windSensorHeight            Integer32,
  windSensorLocation          SnmpAdminString,
  windSensorAvgSpeed          Integer32,
  windSensorAvgDirection      Integer32,
  windSensorSpotSpeed         Integer32,
  windSensorSpotDirection     Integer32,
  windSensorGustSpeed         Integer32,
  windSensorGustDirection     Integer32,
  windSensorSituation         INTEGER,
  windSensorLatitude          Integer32,
  windSensorLongitude         Integer32,
  windSensorModelInformation  Integer32,
  windSensorXOffset           ITSInteger16,
  windSensorYOffset           ITSInteger16,
  windSensorZOffset           ITSInteger16,
  windSensorEntityID          PhysicalIndexOrZero
}

-- 5.6.10.1 Wind Sensor Index
windSensorIndex OBJECT-TYPE
  SYNTAX       Integer32 (1..255)
  MAX-ACCESS   read-only
  STATUS       current
  DESCRIPTION
    "<Definition> Enumerated list of row entries that provide wind sensor data. The first entry shall be that of the primary wind sensor.
    <Parameter Type> status
    <Object Identifier> 1.3.6.1.4.1.1206.4.2.5.2.4.8.1.1"
::= { windSensorEntry 1 }

-- 5.6.10.2 Wind Sensor Height
-- This object has been deprecated.
windSensorHeight OBJECT-TYPE
  SYNTAX       Integer32 (-1000..1001)
  UNITS        "meters"
  MAX-ACCESS   read-write
  STATUS       deprecated
  DESCRIPTION
    "<Definition> The height of the wind sensor with respect to the essReferenceHeight in meters.
    <Format>
The value of 1001 shall indicate a missing value.
    <Parameter Type> configuration
    <Superseded by> windSensorZOffset
    <Informative> Changed to read-write from read-only in version 04. This object was deprecated in version 05. 
    <Object Identifier> 1.3.6.1.4.1.1206.4.2.5.2.4.8.1.2"
::= { windSensorEntry 2 }

-- 5.6.10.3 Wind Sensor Location
windSensorLocation OBJECT-TYPE
  SYNTAX       SnmpAdminString
  MAX-ACCESS   read-write
  STATUS       current
  DESCRIPTION
    "<Definition> A textual string indicating the location of the wind sensor.
    <Parameter Type> configuration
    <Object Identifier> 1.3.6.1.4.1.1206.4.2.5.2.4.8.1.3"
::= { windSensorEntry 3 }

-- 5.6.10.4 Wind Sensor Average Speed
windSensorAvgSpeed OBJECT-TYPE
  SYNTAX       Integer32 (0..65535)
  UNITS        "tenths of meters per second"
  MAX-ACCESS   read-only
  STATUS       current
  DESCRIPTION
    "<Definition> A two-minute average of the wind speed in tenths of meters per second as measured by the wind sensor.
    <Format>
The value of 65535 shall indicate an error condition or missing value.
    <Parameter Type> status
    <Object Identifier> 1.3.6.1.4.1.1206.4.2.5.2.4.8.1.4"
  REFERENCE    "WMO Binary Code Form FM 94 BUFR Table B item 0 11 002."
::= { windSensorEntry 4 }

-- 5.6.10.5 Wind Sensor Average Direction
windSensorAvgDirection OBJECT-TYPE
  SYNTAX       Integer32 (0..361)
  UNITS        "compass degrees"
  MAX-ACCESS   read-only
  STATUS       current
  DESCRIPTION
    "<Definition> A two minute mode (average) of the direction from which the wind is blowing measured clockwise in degrees from true north as measured by the wind sensor.
    <Format>
The value of zero (0) shall indicate 'calm', when the associated speed is zero (0), or 'light and variable,' when the associated speed is greater than zero (0). Normal observations, as defined by the WMO, shall report a wind direction in the range of 1 to 360 with 90 meaning from the east and 360 meaning from the north. The value of 361 shall indicate an error condition and shall always be reported if the associated speed indicates error.
    <Parameter Type> status
    <Object Identifier> 1.3.6.1.4.1.1206.4.2.5.2.4.8.1.5"
  REFERENCE    "WMO Code Form FM 94 BUFR Table B item 0 11 001."
::= { windSensorEntry 5 }

-- 5.6.10.6 Wind Sensor Spot Speed
windSensorSpotSpeed OBJECT-TYPE
  SYNTAX       Integer32 (0..65535)
  UNITS        "tenths of meters per second"
  MAX-ACCESS   read-only
  STATUS       current
  DESCRIPTION
    "<Definition> The wind speed in tenths of meters per second measured by the wind sensor. For mobile platforms, the wind speed shall be corrected for vehicle movement.
    <Format>
The value of 65535 shall indicate an error condition or missing value.
    <Parameter Type> status
    <Object Identifier> 1.3.6.1.4.1.1206.4.2.5.2.4.8.1.6"
::= { windSensorEntry 6 }

-- 5.6.10.7 Wind Sensor Spot Direction
windSensorSpotDirection OBJECT-TYPE
  SYNTAX       Integer32 (0..361)
  UNITS        "compass degrees"
  MAX-ACCESS   read-only
  STATUS       current
  DESCRIPTION
    "<Definition> The direction from which the wind is blowing measured in degrees clockwise from true North as measured by the wind sensor. For mobile platforms, the wind direction shall be corrected for vehicle movement.
    <Format>
The value of zero (0) shall indicate 'calm', when the associated speed is zero (0), or 'light and variable,' when the associated speed is greater than zero (0). Normal observations, as defined by the WMO, shall report a wind direction in the range of 1 to 360 with 90 meaning from the east and 360 meaning from the north. The value of 361 shall indicate an error condition and shall always be reported if the associated speed indicates error.
    <Parameter Type> status
    <Object Identifier> 1.3.6.1.4.1.1206.4.2.5.2.4.8.1.7"
::= { windSensorEntry 7 }

-- 5.6.10.8 Wind Sensor Gust Speed
windSensorGustSpeed OBJECT-TYPE
  SYNTAX       Integer32 (0..65535)
  UNITS        "tenths of meters per second"
  MAX-ACCESS   read-only
  STATUS       current
  DESCRIPTION
    "<Definition> The maximum wind gust recorded by the wind sensor during the 10 minutes preceding the observation measured in tenths of meters per second.
    <Format>
The value of 65535 shall indicate an error condition or missing value.
    <Parameter Type> status
    <Object Identifier> 1.3.6.1.4.1.1206.4.2.5.2.4.8.1.8"
  REFERENCE    "WMO Code Form FM 94 BUFR Table B item 0 11 041."
::= { windSensorEntry 8 }

-- 5.6.10.9 Wind Sensor Gust Direction
windSensorGustDirection OBJECT-TYPE
  SYNTAX       Integer32 (0..361)
  UNITS        "compass degrees"
  MAX-ACCESS   read-only
  STATUS       current
  DESCRIPTION
    "<Definition> The direction of the maximum wind gust recorded during the 10 minutes preceding the observation measured in degrees clockwise from true North by the wind sensor.
    <Format>
The value of zero (0) shall indicate 'calm', when the associated speed is zero (0), or 'light and variable,' when the associated speed is greater than zero (0). Normal observations, as defined by the WMO, shall report a wind direction in the range of 1 to 360 with 90 meaning from the east and 360 meaning from the north. The value of 361 shall indicate an error condition and shall always be reported if the associated speed indicates error.
    <Parameter Type> status
    <Object Identifier> 1.3.6.1.4.1.1206.4.2.5.2.4.8.1.9"
  REFERENCE    "WMO Code Form FM 94 BUFR Table B item 0 11 043."
::= { windSensorEntry 9 }

-- 5.6.10.10 Wind Sensor Situation
windSensorSituation OBJECT-TYPE
  SYNTAX       INTEGER {
    other (1),
    unknown (2),
    calm (3),
    lightBreeze (4),
    moderateBreeze (5),
    strongBreeze (6),
    gale (7),
    moderateGale (8),
    strongGale (9),
    stormWinds (10),
    hurricaneForceWinds (11),
    gustyWinds (12) }
  MAX-ACCESS   read-only
  STATUS       current
  DESCRIPTION
    "<Definition> The assessment of the wind situation from the sensor as defined by the Beaufort Wind Scale in the Glossary of Meteorology.  Specific ranges for these values are defined in the Glossary of Meteorology.
    <Format>
Range               Meaning (WMO Classification)
other               not defined within this standard, see  
                    manufacturer's documentation 
unknown             Unknown conditions 
calm                Calm - Light air
lightBreeze         Light breeze - Gentle breeze
moderateBreeze      Moderate breeze - Fresh breeze
strongBreeze        Strong breeze 
gale                Near Gale 
moderateGale        Gale 
strongGale          Strong gale 
stormWinds          Storm 
hurricaneForceWinds Violent Storm - Hurricane
gustyWinds          defined by a peak and a lull of greater than 46.3 
                    tenths of meters per second within a 2-minute 
                    period.
    <Parameter Type> status
    <Object Identifier> 1.3.6.1.4.1.1206.4.2.5.2.4.8.1.10"
::= { windSensorEntry 10 }

-- 5.6.10.11 Wind Sensor Latitude
-- This object has been deprecated.
windSensorLatitude OBJECT-TYPE
  SYNTAX       Integer32 (-90000000..90000001)
  UNITS        "microdegrees latitude"
  MAX-ACCESS   read-write
  STATUS       deprecated
  DESCRIPTION
    "<Definition> The latitude in 10^-6 degrees of the ESS wind sensor, per WGS-84 datum. 
    <Format>
The windSensorLatitude at the North Pole is 90,000,000. The windSensorLatitude at the South Pole is -90,000,000. The value 90,000,001 shall indicate a missing value.
    <Parameter Type> configuration
    <Superseded by> windSensorYOffset
    <Informative> This object was deprecated in version 05. 
    <Object Identifier> 1.3.6.1.4.1.1206.4.2.5.2.4.8.1.11"
  REFERENCE    "Resolution based on on-going location referencing activities; the WMO Binary Code Form FM 94 BUFR Table B item 0 05 001 can be obtained by dividing this value by 10."
::= { windSensorEntry 11 }

-- 5.6.10.12 Wind Sensor Longitude
-- This object has been deprecated.
windSensorLongitude OBJECT-TYPE
  SYNTAX       Integer32 (-180000000..180000001)
  UNITS        "microdegrees longitude"
  MAX-ACCESS   read-write
  STATUS       deprecated
  DESCRIPTION
    "<Definition> The east longitude in 10^-6 degrees from the Prime Meridian of the ESS wind sensor location. 
    <Format>
The windSensorLongitude of 180 degrees West shall be -180,000,000. The windSensorLongitude of 180 degrees East shall be 180,000,000. The value 180,000,001 shall indicate a missing value.
    <Parameter Type> configuration
    <Superseded by> windSensorXOffset
    <Informative> This object was deprecated in version 05. 
    <Object Identifier> 1.3.6.1.4.1.1206.4.2.5.2.4.8.1.12"
  REFERENCE    "Resolution based on on-going location referencing activities; the WMO Binary Code Form FM 94 BUFR Table B item 0 06 001 can be obtained by dividing this value by 10."
::= { windSensorEntry 12 }

-- 5.6.10.13 Wind Sensor Model Information
-- This object has been deprecated.
windSensorModelInformation OBJECT-TYPE
  SYNTAX       Integer32 (0..255)
  MAX-ACCESS   read-only
  STATUS       deprecated
  DESCRIPTION
    "<Definition> Indicates the row in the Module Table (See NTCIP 1201) that contains information about the make, model, and version number of the sensor associated with this row of the Wind Sensor Table.
    <Format>
The value of zero indicates that this information is not available.
    <Parameter Type> status
    <Supplanted by> windSensorEntityID
    <Informative> This object was deprecated in version 05.
    <Object Identifier> 1.3.6.1.4.1.1206.4.2.5.2.4.8.1.13"
::= { windSensorEntry 13 }

-- 5.6.10.14 Wind Sensor X Offset
windSensorXOffset OBJECT-TYPE
  SYNTAX       ITSInteger16
  UNITS        "centimeters"
  MAX-ACCESS   read-write
  STATUS       current
  DESCRIPTION
    "<Definition> The X offset of the wind sensor from the field device's reference location as defined by fdConfiguredLatitude and fdConfiguredLongitude. 
    <Format>
For stationary devices, the X offset shall indicate the eastward (positive) or westward (negative) distance from the reference location. For transportable and mobile devices, the X offset shall indicate distances to the starboard side (positive) or port side (negative) of the reference location on the vehicle.
    <Parameter Type> configuration
    <Object Identifier> 1.3.6.1.4.1.1206.4.2.5.2.4.8.1.14"
::= { windSensorEntry 14 }

-- 5.6.10.15 Wind Sensor Y Offset
windSensorYOffset OBJECT-TYPE
  SYNTAX       ITSInteger16
  UNITS        "centimeters"
  MAX-ACCESS   read-write
  STATUS       current
  DESCRIPTION
    "<Definition> The Y offset of the wind sensor from the field device's reference location as defined by fdConfiguredLatitude and fdConfiguredLongitude. 
    <Format>
For stationary devices, the Y offset shall indicate the northward (positive) or southward (negative) distance from the reference location. For transportable and mobile devices, the Y offset shall indicate distances to the fore (positive) or aft (negative) of the reference location on the vehicle.
    <Parameter Type> configuration
    <Object Identifier> 1.3.6.1.4.1.1206.4.2.5.2.4.8.1.15"
::= { windSensorEntry 15 }

-- 5.6.10.16 Wind Sensor Z Offset
windSensorZOffset OBJECT-TYPE
  SYNTAX       ITSInteger16
  UNITS        "centimeters"
  MAX-ACCESS   read-write
  STATUS       current
  DESCRIPTION
    "<Definition> The offset elevation of the wind sensor from the fdConfiguredElevation in centimeters.
    <Format>
Upward offsets shall be positive and downward offsets shall be negative. 
    <Parameter Type> configuration
    <Object Identifier> 1.3.6.1.4.1.1206.4.2.5.2.4.8.1.16"
::= { windSensorEntry 16 }

-- 5.6.10.17 Wind Sensor Entity ID
windSensorEntityID OBJECT-TYPE
  SYNTAX       PhysicalIndexOrZero
  MAX-ACCESS   read-only
  STATUS       current
  DESCRIPTION
    "<Definition> Indicates the row in the entPhysicalTable (See RFC 4133) that contains information about the sensor, such as the manufacturer, model, and hardware and software revision identifiers. 
    <Format>
The value of zero indicates that this information is not available.
    <Parameter Type> status
    <Informative> The mechanism used to configure this value when adding or modifying a sensor is not defined by this document and is considered manufacturer-specific.
    <Object Identifier> 1.3.6.1.4.1.1206.4.2.5.2.4.8.1.17"
::= { windSensorEntry 17 }

-- 5.7 Temperature Data Objects
essNtcipTemperature OBJECT-IDENTITY
    STATUS       current
  DESCRIPTION
    "<Definition> Objects used to describe the temperature data that is collected at the ESS.
    <Object Identifier> 1.3.6.1.4.1.1206.4.2.5.2.5"
::= {essNtcip 5}

-- 5.7.1 Number of Temperature Sensors
essNumTemperatureSensors OBJECT-TYPE
  SYNTAX       Integer32 (0..255)
  UNITS        "sensors"
  MAX-ACCESS   read-only
  STATUS       current
  DESCRIPTION
    "<Definition> Indicates the number of entries in the temperature sensor table.
    <Parameter Type> status
    <Informative> This value may automatically change upon connecting or disconnecting a sensor; however, the table is still defined as a static table since the creation/deletion of rows is not managed through SNMP logic.
    <Object Identifier> 1.3.6.1.4.1.1206.4.2.5.2.5.1"
::= { essNtcipTemperature 1 }

-- 5.7.2 Temperature Sensor Table
essTemperatureSensorTable OBJECT-TYPE
  SYNTAX       SEQUENCE OF EssTemperatureSensorEntry
  MAX-ACCESS   not-accessible
  STATUS       current
  DESCRIPTION
    "<Definition> Table containing the temperature sensor data fields.
    <Object Identifier> 1.3.6.1.4.1.1206.4.2.5.2.5.2"
::= { essNtcipTemperature 2 }

-- 5.7.3 Temperature Sensor
essTemperatureSensorEntry OBJECT-TYPE
  SYNTAX       EssTemperatureSensorEntry
  MAX-ACCESS   not-accessible
  STATUS       current
  DESCRIPTION
    "<Definition> Parameters for specific temperature sensor as described through a number of attributes as indicated by the following subclauses."
  INDEX { essTemperatureSensorIndex }
::= { essTemperatureSensorTable 1 }

EssTemperatureSensorEntry ::= SEQUENCE {
  essTemperatureSensorIndex             Integer32,
  essTemperatureSensorHeight            Integer32,
  essAirTemperature                     Integer32, 
  essTemperatureSensorLatitude          Integer32,
  essTemperatureSensorLongitude         Integer32,
  essTemperatureSensorLocation          SnmpAdminString,
  essTemperatureSensorModelInformation  Integer32,
  essTemperatureSensorXOffset           ITSInteger16,
  essTemperatureSensorYOffset           ITSInteger16,
  essTemperatureSensorZOffset           ITSInteger16,
  essTemperatureSensorEntityID          PhysicalIndexOrZero}

-- 5.7.3.1 Temperature Sensor Index
essTemperatureSensorIndex OBJECT-TYPE
  SYNTAX       Integer32 (1..255)
  MAX-ACCESS   read-only
  STATUS       current
  DESCRIPTION
    "<Definition> Enumerated list of row entries that provide temperature sensor data.
    <Parameter Type> status
    <Object Identifier> 1.3.6.1.4.1.1206.4.2.5.2.5.2.1.1"
::= { essTemperatureSensorEntry 1 }

-- 5.7.3.2 Temperature Sensor Height
-- This object has been deprecated.
essTemperatureSensorHeight OBJECT-TYPE
  SYNTAX       Integer32 (-1000..1001)
  UNITS        "meters"
  MAX-ACCESS   read-write
  STATUS       deprecated
  DESCRIPTION
    "<Definition> The height of the temperature sensor as measured in meters above essReferenceHeight.
    <Format>
The value 1001 shall indicate a missing value.
    <Parameter Type> configuration
    <Superseded by> essTemperatureSensorZOffset
    <Informative> Changed to read-write from read-only in version 04. This object was deprecated in version 05. 
    <Object Identifier> 1.3.6.1.4.1.1206.4.2.5.2.5.2.1.2"
::= { essTemperatureSensorEntry 2 }

-- 5.7.3.3 Air Temperature
essAirTemperature OBJECT-TYPE
  SYNTAX       Integer32 (-1000..1001)
  UNITS        "tenths of degrees Celsius"
  MAX-ACCESS   read-only
  STATUS       current
  DESCRIPTION
    "<Definition> The dry-bulb temperature in tenths of degrees Celsius. The temperature is an instantaneous reading at the height specified by essTemperatureSensorHeight.
    <Format>
The value 1001 shall indicate an error condition or missing value.
    <Parameter Type> status
    <Object Identifier> 1.3.6.1.4.1.1206.4.2.5.2.5.2.1.3"
  REFERENCE    "Resolution is based on WMO Binary Code Form FM 94 BUFR Table B item 0 12 001; temperature in Kelvin is determined by adding 273.15 to this value."
::= { essTemperatureSensorEntry 3 }

-- 5.7.3.4 Temperature Sensor Latitude
-- This object has been deprecated.
essTemperatureSensorLatitude OBJECT-TYPE
  SYNTAX       Integer32 (-90000000..90000001)
  UNITS        "microdegrees latitude"
  MAX-ACCESS   read-write
  STATUS       deprecated
  DESCRIPTION
    "<Definition> The latitude in 10^-6 degrees of the ESS temperature sensor, per WGS-84 datum. 
    <Format>
The essTemperatureSensorLatitude at the North Pole is 90,000,000. The essTemperatureSensorLatitude at the South Pole is -90,000,000. The value 90,000,001 shall indicate a missing value.
    <Parameter Type> configuration
    <Superseded by> essTemperatureSensorYOffset
    <Informative> This object was deprecated in version 05. 
    <Object Identifier> 1.3.6.1.4.1.1206.4.2.5.2.5.2.1.4"
  REFERENCE    "Resolution based on on-going location referencing activities; the WMO Binary Code Form FM 94 BUFR Table B item 0 05 001 can be obtained by dividing this value by 10."
::= { essTemperatureSensorEntry 4 }

-- 5.7.3.5 Temperature Sensor Longitude
-- This object has been deprecated.
essTemperatureSensorLongitude OBJECT-TYPE
  SYNTAX       Integer32 (-180000000..180000001)
  UNITS        "microdegrees longitude"
  MAX-ACCESS   read-write
  STATUS       deprecated
  DESCRIPTION
    "<Definition> The east longitude in 10^-6 degrees from the Prime Meridian of the ESS temperature sensor location. 
    <Format>
The essTemperatureSensorLongitude of 180 degrees West shall be -180,000,000. The essTemperatureSensorLongitude  of 180 degrees East shall be 180,000,000. The value 180,000,001 shall indicate a missing value.
    <Parameter Type> configuration
    <Superseded by> essTemperatureSensorXOffset
    <Informative> This object was deprecated in version 05. 
    <Object Identifier> 1.3.6.1.4.1.1206.4.2.5.2.5.2.1.5"
  REFERENCE    "Resolution based on on-going location referencing activities; the WMO Binary Code Form FM 94 BUFR Table B item 0 06 001 can be obtained by dividing this value by 10."
::= { essTemperatureSensorEntry 5 }

-- 5.7.3.6 Temperature Sensor Location
essTemperatureSensorLocation OBJECT-TYPE
  SYNTAX       SnmpAdminString
  MAX-ACCESS   read-write
  STATUS       current
  DESCRIPTION
    "<Definition> A textual string indicating the location of the temperature sensor.
    <Parameter Type> configuration
    <Object Identifier> 1.3.6.1.4.1.1206.4.2.5.2.5.2.1.6"
::= { essTemperatureSensorEntry 6 }

-- 5.7.3.7 Temperature Sensor Model Information
-- This object has been deprecated.
essTemperatureSensorModelInformation OBJECT-TYPE
  SYNTAX       Integer32 (0..255)
  MAX-ACCESS   read-write
  STATUS       deprecated
  DESCRIPTION
    "<Definition> Indicates the row in the Module Table (See NTCIP 1201) that contains information about the make, model, and version number of the sensor associated with this row of the Temperature Sensor Table.
    <Format>
The value of zero indicates that this information is not available.
    <Parameter Type> configuration
    <Supplanted by> essTemperatureSensorEntityID
    <Informative> This object was deprecated in version 05.
    <Object Identifier> 1.3.6.1.4.1.1206.4.2.5.2.5.2.1.7"
::= { essTemperatureSensorEntry 7 }

-- 5.7.3.8 Temperature Sensor X Offset
essTemperatureSensorXOffset OBJECT-TYPE
  SYNTAX       ITSInteger16
  UNITS        "centimeters"
  MAX-ACCESS   read-write
  STATUS       current
  DESCRIPTION
    "<Definition> The lateral offset of the temperature sensor from the field device's reference location as defined by fdConfiguredLatitude and fdConfiguredLongitude. 
    <Format>
For stationary devices, the X offset shall indicate the eastward (positive) or westward (negative) distance from the reference location. For transportable and mobile devices, the X offset shall indicate distances to the starboard side (positive) or port side (negative) of the reference location on the vehicle.
    <Parameter Type> configuration
    <Object Identifier> 1.3.6.1.4.1.1206.4.2.5.2.5.2.1.8"
::= { essTemperatureSensorEntry 8 }

-- 5.7.3.9 Temperature Sensor Y Offset
essTemperatureSensorYOffset OBJECT-TYPE
  SYNTAX       ITSInteger16
  UNITS        "centimeters"
  MAX-ACCESS   read-write
  STATUS       current
  DESCRIPTION
    "<Definition> The Y offset of the temperature sensor from the field device's reference location as defined by fdConfiguredLatitude and fdConfiguredLongitude. 
    <Format>
For stationary devices, the Y offset shall indicate the northward (positive) or southward (negative) distance from the reference location. For transportable and mobile devices, the Y offset shall indicate distances to the fore (positive) or aft (negative) of the reference location on the vehicle.
    <Parameter Type> configuration
    <Object Identifier> 1.3.6.1.4.1.1206.4.2.5.2.5.2.1.9"
::= { essTemperatureSensorEntry 9 }

-- 5.7.3.10 Temperature Sensor Z Offset
essTemperatureSensorZOffset OBJECT-TYPE
  SYNTAX       ITSInteger16
  UNITS        "centimeters"
  MAX-ACCESS   read-write
  STATUS       current
  DESCRIPTION
    "<Definition> The offset elevation of the temperature sensor from the fdConfiguredElevation in centimeters.
    <Format>
Upward offsets shall be positive and downward offsets shall be negative. 
    <Parameter Type> configuration
    <Object Identifier> 1.3.6.1.4.1.1206.4.2.5.2.5.2.1.10"
::= { essTemperatureSensorEntry 10 }

-- 5.7.3.11 Temperature Sensor Entity ID
essTemperatureSensorEntityID OBJECT-TYPE
  SYNTAX       PhysicalIndexOrZero
  MAX-ACCESS   read-only
  STATUS       current
  DESCRIPTION
    "<Definition> Indicates the row in the entPhysicalTable (See RFC 4133) that contains information about the sensor, such as the manufacturer, model, and hardware and software revision identifiers. 
    <Format>
The value of zero indicates that this information is not available.
    <Parameter Type> status
    <Informative> The mechanism used to configure this value when adding or modifying a sensor is not defined by this document and is considered manufacturer-specific.
    <Object Identifier> 1.3.6.1.4.1.1206.4.2.5.2.5.2.1.11"
::= { essTemperatureSensorEntry 11 }

-- 5.7.4 Wetbulb Temperature
-- This object has been deprecated.
essWetbulbTemp OBJECT-TYPE
  SYNTAX       Integer32 (-1000..1001)
  UNITS        "tenths of degrees Celsius"
  MAX-ACCESS   read-only
  STATUS       deprecated
  DESCRIPTION
    "<Definition> The wet-bulb temperature in tenths of degrees Celsius. The temperature is an instantaneous reading by the temperature sensor specified in the first row of the essTemperatureTable. 
    <Format>
The value 1001 shall indicate an error condition or missing value.
    <Parameter Type> status
    <Supplanted by> humiditySensorWetbulbTemp
    <Informative> This object was deprecated in version 05.
    <Object Identifier> 1.3.6.1.4.1.1206.4.2.5.2.5.3"
  REFERENCE    "is based on WMO Binary Code Form FM 94 BUFR Table B item 0 12 002; temperature in Kelvin is determined by adding 273.15 to this value."
::= { essNtcipTemperature 3 }

-- 5.7.5 Dewpoint Temperature
-- This object has been deprecated.
essDewpointTemp OBJECT-TYPE
  SYNTAX       Integer32 (-1000..1001)
  UNITS        "tenths of degrees Celsius"
  MAX-ACCESS   read-only
  STATUS       deprecated
  DESCRIPTION
    "<Definition> The dewpoint temperature in tenths of degrees Celsius. The temperature is an instantaneous reading by the temperature sensor specified in the first row specified of the essTemperatureSensorTable. 
    <Format>
The value 1001 shall indicate an error condition or missing value.
    <Parameter Type> status
    <Supplanted by> humiditySensorDewpointTemp
    <Informative> This object was deprecated in version 05.
    <Object Identifier> 1.3.6.1.4.1.1206.4.2.5.2.5.4"
  REFERENCE    "Resolution is based on WMO Binary Code Form FM 94 BUFR Table B item 0 12 003; temperature in Kelvin is determined by adding 273.15 to this value."
::= { essNtcipTemperature 4 }

-- 5.7.6 Maximum Temperature
essMaxTemp OBJECT-TYPE
  SYNTAX       Integer32 (-1000..1001)
  UNITS        "tenths of degrees Celsius"
  MAX-ACCESS   read-only
  STATUS       current
  DESCRIPTION
    "<Definition> The maximum temperature in tenths of degrees Celsius recorded during the 24 hours preceding the observation by the temperature sensor specified in the first row of the essTemperatureSensorTable. 
    <Format>
The value 1001 shall indicate an error condition or missing value.
    <Parameter Type> status
    <Object Identifier> 1.3.6.1.4.1.1206.4.2.5.2.5.5"
  REFERENCE    "Resolution is based on WMO Binary Code Form FM 94 BUFR Table B item 0 12 011; temperature in Kelvin is determined by adding 273.15 to this value."
::= { essNtcipTemperature 5 }

-- 5.7.7 Minimum Temperature
essMinTemp OBJECT-TYPE
  SYNTAX       Integer32 (-1000..1001)
  UNITS        "tenths of degrees Celsius"
  MAX-ACCESS   read-only
  STATUS       current
  DESCRIPTION
    "<Definition> The minimum temperature in tenths of degrees Celsius recorded during the 24 hours preceding the observation by the temperature sensor specified in the first row of the essTemperatureSensorTable.
    <Format>
The value 1001 shall indicate an error condition or missing value.
    <Parameter Type> status
    <Object Identifier> 1.3.6.1.4.1.1206.4.2.5.2.5.6"
  REFERENCE    "Resolution is based on WMO Binary Code Form FM 94 BUFR Table B item 0 12 012; temperature in Kelvin is determined by adding 273.15 to the Celsius value."
::= { essNtcipTemperature 6 }

-- 5.8 Humidity and Precipitation Data Objects
essBufrPrecip OBJECT-IDENTITY
    STATUS       current
  DESCRIPTION
    "<Definition> Objects used to describe the humidity and precipitation data collected by the ESS and presented in BUFR-equivalent formats.
    <Object Identifier> 1.3.6.1.4.1.1206.4.2.5.1.13"
::= {essBufr 13 }

essNtcipPrecip OBJECT-IDENTITY
    STATUS       current
  DESCRIPTION
    "<Definition> Objects used to describe the humidity and precipitation data collected by the ESS and presented in a format not defined by BUFR.
    <Object Identifier> 1.3.6.1.4.1.1206.4.2.5.2.6"
::= {essNtcip 6 }

-- 5.8.1 Relative Humidity
-- This object has been deprecated.
essRelativeHumidity OBJECT-TYPE
  SYNTAX       Integer32 (0..101)
  UNITS        "percent humidity"
  MAX-ACCESS   read-only
  STATUS       deprecated
  DESCRIPTION
    "<Definition> The relative humidity in percent. 
    <Format>
The value of 101 shall indicate an error condition or missing value.
    <Parameter Type> status
    <Superseded by> humiditySensorRelativeHumidity.1
    <Informative> This object was deprecated in version 04. 
    <Object Identifier> 1.3.6.1.4.1.1206.4.2.5.1.13.3"
  REFERENCE    "WMO Binary Code Form FM 94 BUFR Table B item 0 13 003."
::= { essBufrPrecip 3 }

-- 5.8.2 Water Depth
-- This object has been deprecated.
essWaterDepth OBJECT-TYPE
  SYNTAX       Integer32 (0..65535)
  UNITS        "centimeters"
  MAX-ACCESS   read-only
  STATUS       deprecated
  DESCRIPTION
    "<Definition> Indicates the depth of the water from a user-defined point in centimeters. The value of 65535 shall indicate an error condition or missing value. This may be used for stream depth, depth of water over a roadway, reservoir depth, or other such uses.
    <Parameter Type> status
    <Superseded by> waterLevelSensorReading.1
    <Informative> This object was deprecated in version 02. 
    <Object Identifier> 1.3.6.1.4.1.1206.4.2.5.2.6.1"
::= { essNtcipPrecip 1 }

-- 5.8.3 Adjacent Snow Depth
-- This object has been deprecated.
essAdjacentSnowDepth OBJECT-TYPE
  SYNTAX       Integer32 (0..3001)
  UNITS        "centimeters"
  MAX-ACCESS   read-only
  STATUS       deprecated
  DESCRIPTION
    "<Definition> The depth of snow in centimeters on representative areas other than the highway pavement, avoiding drifts and plowed areas. 
    <Format>
The value 3001 shall indicate an error condition or missing value.
    <Parameter Type> status
    <Superseded by> precipitationSensorAdjacentSnowDepth.1
    <Informative> This object was deprecated in version 04. 
    <Object Identifier> 1.3.6.1.4.1.1206.4.2.5.2.6.2"
::= { essNtcipPrecip 2 }

-- 5.8.4 Roadway Snow Depth
-- This object has been deprecated.
essRoadwaySnowDepth OBJECT-TYPE
  SYNTAX       Integer32 (0..3001)
  UNITS        "centimeters"
  MAX-ACCESS   read-only
  STATUS       deprecated
  DESCRIPTION
    "<Definition> The current depth of unpacked snow in centimeters on the driving surface. 
    <Format>
The value 3001 shall indicate an error condition or missing value.
    <Parameter Type> status
    <Superseded by> precipitationSensorRoadwaySnowDepth.1
    <Informative> This object was deprecated in version 04. 
    <Object Identifier> 1.3.6.1.4.1.1206.4.2.5.2.6.3"
::= { essNtcipPrecip 3 }

-- 5.8.5 Roadway Snow Pack Depth
-- This object has been deprecated.
essRoadwaySnowPackDepth OBJECT-TYPE
  SYNTAX       Integer32 (0..3001)
  UNITS        "centimeters"
  MAX-ACCESS   read-only
  STATUS       deprecated
  DESCRIPTION
    "<Definition> The current depth of packed snow in centimeters on the roadway surface. 
    <Format>
The value 3001 shall indicate an error condition or missing value.
    <Parameter Type> status
    <Superseded by> precipitationSensorRoadwaySnowPackDepth.1
    <Informative> This object was deprecated in version 04. 
    <Object Identifier> 1.3.6.1.4.1.1206.4.2.5.2.6.4"
::= { essNtcipPrecip 4 }

-- 5.8.6 Precipitation Indicator
-- This object has been deprecated.
essPrecipYesNo OBJECT-TYPE
  SYNTAX       INTEGER {
    precip (1),
    noPrecip (2),
    error (3) }
  MAX-ACCESS   read-only
  STATUS       deprecated
  DESCRIPTION
    "<Definition> Indicates whether or not moisture is detected by the sensor.
    <Format>
precip - Moisture is currently being detected by the precipitation sensor
noPrecip - Moisture is not currently being detected by the precipitation 
    sensor
error - The sensor is either not connected, not reporting, or is 
    indicating an error
    <Parameter Type> status
    <Superseded by> precipitationSensorPrecipYesNo.1
    <Informative> This object was deprecated in version 04. 
    <Object Identifier> 1.3.6.1.4.1.1206.4.2.5.2.6.5"
::= { essNtcipPrecip 5 }

-- 5.8.7 Rainfall or Water Equivalent of Snow
-- This object has been deprecated.
essPrecipRate OBJECT-TYPE
  SYNTAX       Integer32 (0..65535)
  UNITS        "tenths of grams per square meter per second"
  MAX-ACCESS   read-only
  STATUS       deprecated
  DESCRIPTION
    "<Definition> The rainfall, or water equivalent of snow, rate in tenths of grams per square meter per second (for rain, this is approximately to 0.36 mm/hr). 
    <Format>
The value of 65535 shall indicate an error condition or missing value.
    <Parameter Type> status
    <Superseded by> precipitationSensorPrecipRate.1
    <Informative> This object was deprecated in version 04. 
    <Object Identifier> 1.3.6.1.4.1.1206.4.2.5.1.13.14"
  REFERENCE    "WMO Binary Code Form FM 94 BUFR Table B item 0 13 014."
::= { essBufrPrecip 14 }

-- 5.8.8 Snowfall Accumulation Rate
-- This object has been deprecated.
essSnowfallAccumRate OBJECT-TYPE
  SYNTAX       Integer32 (0..65535)
  UNITS        "10^-7 meters per second"
  MAX-ACCESS   read-only
  STATUS       deprecated
  DESCRIPTION
    "<Definition> The snowfall accumulation rate in 10^-7 meters per second (this is equivalent to 0.36 mm/hr). 
    <Format>
The value 65535 shall indicate an error condition or missing value.
    <Parameter Type> status
    <Superseded by> precipitationSensorSnowfallAccumRate.1
    <Informative> This object was deprecated in version 04. 
    <Object Identifier> 1.3.6.1.4.1.1206.4.2.5.1.13.15"
  REFERENCE    "WMO Binary Code Form FM 94 BUFR Table B item 0 13 015."
::= { essBufrPrecip 15 }

-- 5.8.9 Precipitation Situation
essPrecipSituation OBJECT-TYPE
  SYNTAX       INTEGER {
    other (1),
    unknown (2),
    noPrecipitation (3),
    unidentifiedSlight (4),
    unidentifiedModerate (5),
    unidentifiedHeavy (6),
    snowSlight (7),
    snowModerate (8),
    snowHeavy (9),
    rainSlight (10),
    rainModerate (11),
    rainHeavy (12),
    frozenPrecipitationSlight (13),
    frozenPrecipitationModerate (14),
    frozenPrecipitationHeavy (15) }
  MAX-ACCESS   read-only
  STATUS       current
  DESCRIPTION
    "<Definition> Describes the weather situation in terms of precipitation. For automated stations, describes the intensity and precipitation type as specified in the first row of the precipitationSensorTable.
    <Format>
Intensity     Meaning 
slight      < 2mm/h water equivalent 
moderate    >= 2 and < 8 mm/h water equivalent 
heavy       >= 8 mm/h water equivalent If one exists, the corresponding 
            BUFR value is indicated for staffed (BUFRs) and automated 
            (BUFRa) stations. The indicated value can be found in the 
            BUFR Table referenced below. Defined values are: 
Range   BUFRa   BUFRs  Meaning 
1                      other 
2                      unknown  
3                      no precipitation 
4                      unidentified slight 
5                      unidentified moderate 
6                      unidentified heavy 
7       171      85    snow slight 
8       172      86    snow moderate 
9       173      86    snow heavy 
10               61    rain slight 
11      165      63    rain moderate 
12      163      65    rain heavy 
13                     frozen precipitation slight 
14                     frozen precipitation moderate 
15                     frozen precipitation heavy
    <Parameter Type> status
    <Informative> Starting in NTCIP 1204 v05; this object should only report human readings; automated sensors should use precipitationSensorPrecipSituation (See 5.8.24.14). 
    <Object Identifier> 1.3.6.1.4.1.1206.4.2.5.2.6.6"
  REFERENCE    "The values identified in the above table for BUFRa and BUFRs can be found in WMO Binary Code Form FM 94 BUFR Table B item 0 20 003."
::= { essNtcipPrecip 6 }

-- 5.8.10 Ice Deposit (Thickness)
-- This object has been deprecated.
essIceThickness OBJECT-TYPE
  SYNTAX       Integer32 (0..65535)
  UNITS        "millimeters"
  MAX-ACCESS   read-only
  STATUS       deprecated
  DESCRIPTION
    "<Definition> Indicates the thickness of the ice in millimeters. 
    <Format>
The value 65535 shall indicate an error condition or missing value.
    <Parameter Type> status
    <Superseded by> precipitationSensorIceThickness.1
    <Informative> This object was deprecated in version 04. 
    <Object Identifier> 1.3.6.1.4.1.1206.4.2.5.2.6.7"
::= { essNtcipPrecip 7 }

-- 5.8.11 Precipitation Start Time
-- This object has been deprecated.
essPrecipitationStartTime OBJECT-TYPE
  SYNTAX       Unsigned32
  UNITS        "seconds"
  MAX-ACCESS   read-only
  STATUS       deprecated
  DESCRIPTION
    "<Definition> The time at which the most recent precipitation event began, measured in seconds since 00:00:00 January 1, 1970 UTC. 
    <Format>
As this standard has been developed long after 1970, a value of 0 for time should indicate to the management station that the data received is suspect.
    <Parameter Type> status
    <Superseded by> precipitationSensorPrecipitationStartTime.1
    <Informative> This object was deprecated in version 04. 
    <Object Identifier> 1.3.6.1.4.1.1206.4.2.5.2.6.8"
::= { essNtcipPrecip 8 }

-- 5.8.12 Precipitation End Time
-- This object has been deprecated.
essPrecipitationEndTime OBJECT-TYPE
  SYNTAX       Unsigned32
  UNITS        "seconds"
  MAX-ACCESS   read-only
  STATUS       deprecated
  DESCRIPTION
    "<Definition> The time at which the most recently completed precipitation event ended, measured in seconds since 00:00:00 January 1, 1970 UTC. 
    <Format>
As this standard has been developed long after 1970, a value of 0 for the time should indicate to the management station that the data received is suspect.
    <Parameter Type> status
    <Superseded by> precipitationSensorPrecipitationEndTime.1
    <Informative> This object was deprecated in version 04. 
    <Object Identifier> 1.3.6.1.4.1.1206.4.2.5.2.6.9"
::= { essNtcipPrecip 9 }

-- 5.8.13 Total Precipitation Past One Hour
-- This object has been deprecated.
essPrecipitationOneHour OBJECT-TYPE
  SYNTAX       Integer32 (0..65535)
  UNITS        "tenths of kilograms per square meter"
  MAX-ACCESS   read-only
  STATUS       deprecated
  DESCRIPTION
    "<Definition> The total water equivalent precipitation over the hour preceding the observation in tenths of kilograms per square meter (for rain, this is approximately tenths of millimeters). 
    <Format>
The value of 65535 shall indicate an error condition or missing value.
    <Parameter Type> status
    <Superseded by> precipitationSensorPrecipitationOneHour.1
    <Informative> This object was deprecated in version 04. 
    <Object Identifier> 1.3.6.1.4.1.1206.4.2.5.1.13.19"
  REFERENCE    "WMO Binary Code Form FM 94 BUFR Table B item 0 13 019."
::= { essBufrPrecip 19 }

-- 5.8.14 Total Precipitation Past Three Hours
-- This object has been deprecated.
essPrecipitationThreeHours OBJECT-TYPE
  SYNTAX       Integer32 (0..65535)
  UNITS        "tenths of kilograms per square meter"
  MAX-ACCESS   read-only
  STATUS       deprecated
  DESCRIPTION
    "<Definition> The total water equivalent precipitation over the three hours preceding the observation in tenths of kilograms per square meter (for rain, this is approximately tenths of millimeters). 
    <Format>
The value of 65535 shall indicate an error condition or missing value.
    <Parameter Type> status
    <Superseded by> precipitationSensorPrecipitationThreeHours.1
    <Informative> This object was deprecated in version 04. 
    <Object Identifier> 1.3.6.1.4.1.1206.4.2.5.1.13.20"
  REFERENCE    "WMO Binary Code Form FM 94 BUFR Table B item 0 13 020."
::= { essBufrPrecip 20 }

-- 5.8.15 Total Precipitation Past Six Hours
-- This object has been deprecated.
essPrecipitationSixHours OBJECT-TYPE
  SYNTAX       Integer32 (0..65535)
  UNITS        "tenths of kilograms per square meter"
  MAX-ACCESS   read-only
  STATUS       deprecated
  DESCRIPTION
    "<Definition> The total water equivalent precipitation over the six hours preceding the observation in tenths of kilograms per square meter (for rain, this is approximately tenths of millimeters). 
    <Format>
The value of 65535 shall indicate an error condition or missing value.
    <Parameter Type> status
    <Superseded by> precipitationSensorPrecipitationSixHours.1
    <Informative> This object was deprecated in version 04. 
    <Object Identifier> 1.3.6.1.4.1.1206.4.2.5.1.13.21"
  REFERENCE    "WMO Binary Code Form FM 94 BUFR Table B item 0 13 021."
::= { essBufrPrecip 21 }

-- 5.8.16 Total Precipitation Past Twelve Hours
-- This object has been deprecated.
essPrecipitationTwelveHours OBJECT-TYPE
  SYNTAX       Integer32 (0..65535)
  UNITS        "tenths of kilograms per square meter"
  MAX-ACCESS   read-only
  STATUS       deprecated
  DESCRIPTION
    "<Definition> The total water equivalent precipitation over the twelve hours preceding the observation in tenths of kilograms per square meter (for rain, this is approximately to tenths of millimeters). 
    <Format>
The value of 65535 shall indicate an error condition or missing value.
    <Parameter Type> status
    <Superseded by> precipitationSensorPrecipitationTwelveHours.1
    <Informative> This object was deprecated in version 04. 
    <Object Identifier> 1.3.6.1.4.1.1206.4.2.5.1.13.22"
  REFERENCE    "WMO Binary Code Form FM 94 BUFR Table B item 0 13 022."
::= { essBufrPrecip 22 }

-- 5.8.17 Total Precipitation Past Twenty-Four Hours
-- This object has been deprecated.
essPrecipitation24Hours OBJECT-TYPE
  SYNTAX       Integer32 (0..65535)
  UNITS        "tenths of kilograms per square meter"
  MAX-ACCESS   read-only
  STATUS       deprecated
  DESCRIPTION
    "<Definition> The total water equivalent precipitation over the twenty-four hours preceding the observation in tenths of kilograms per square meter (for rain, this is equivalent to tenths of millimeters). 
    <Format>
The value of 65535 shall indicate an error condition or missing value.
    <Parameter Type> status
    <Superseded by> precipitationSensorPrecipitation24Hours.1
    <Informative> This object was deprecated in version 04. 
    <Object Identifier> 1.3.6.1.4.1.1206.4.2.5.1.13.23"
  REFERENCE    "WMO Binary Code Form FM 94 BUFR Table B item 0 13 023."
::= { essBufrPrecip 23 }

-- 5.8.18 Precipitation Sensor Model Information
-- This object has been deprecated.
precipitationSensorModelInformation OBJECT-TYPE
  SYNTAX       Integer32 (0..255)
  MAX-ACCESS   read-write
  STATUS       deprecated
  DESCRIPTION
    "<Definition> A reference to the row in the Module Table (See NTCIP 1201) that indicates the manufacturer, model, and version number of the precipitation sensor.
    <Format>
The value of zero indicates that this information is not available.
    <Parameter Type> configuration
    <Superseded by> precipitationSensorModelInformationV4.1
    <Informative> This object was deprecated in version 04. 
    <Object Identifier> 1.3.6.1.4.1.1206.4.2.5.2.6.10"
::= { essNtcipPrecip 10 }

-- 5.8.19 Number of Water Level Sensors
waterLevelSensorTableNumSensors OBJECT-TYPE
  SYNTAX       Integer32 (0..255)
  UNITS        "sensors"
  MAX-ACCESS   read-only
  STATUS       current
  DESCRIPTION
    "<Definition> Indicates the number of entries in the water level sensor table.
    <Parameter Type> status
    <Informative> This value may automatically change upon connecting or disconnecting a sensor; however, the table is still defined as a static table since the creation/deletion of rows is not managed through SNMP logic.
    <Object Identifier> 1.3.6.1.4.1.1206.4.2.5.2.6.11"
::= { essNtcipPrecip 11 }

-- 5.8.20 Water Level Sensor Table
waterLevelSensorTable OBJECT-TYPE
  SYNTAX       SEQUENCE OF WaterLevelSensorEntry
  MAX-ACCESS   not-accessible
  STATUS       current
  DESCRIPTION
    "<Definition> Table containing the water level sensor data fields.
    <Object Identifier> 1.3.6.1.4.1.1206.4.2.5.2.6.12"
::= { essNtcipPrecip 12 }

-- 5.8.21 Water Level Sensor
waterLevelSensorEntry OBJECT-TYPE
  SYNTAX       WaterLevelSensorEntry 
  MAX-ACCESS   not-accessible
  STATUS       current
  DESCRIPTION
    "<Definition> Parameters for a specific water level sensor as described through a number of attributes as indicated by the following subclauses."
  INDEX { waterLevelSensorIndex }
::= { waterLevelSensorTable 1 }

WaterLevelSensorEntry ::= SEQUENCE {  
  waterLevelSensorIndex               Integer32,
  waterLevelSensorReading             Integer32,
  waterLevelSensorWarningLevel        Integer32,
  waterLevelSensorHeight              Integer32,
  waterLevelSensorLatitude            Integer32,
  waterLevelSensorLongitude           Integer32,
  waterLevelSensorLocation            SnmpAdminString,
  waterLevelSensorModelInformation    Integer32,
  waterLevelSensorReferencePoint      SnmpAdminString,
  waterLevelSensorXOffset             ITSInteger16,
  waterLevelSensorYOffset             ITSInteger16,
  waterLevelSensorZOffset             ITSInteger16,
  waterLevelSensorEntityID            PhysicalIndexOrZero }

-- 5.8.21.1 Water Level Sensor Index
waterLevelSensorIndex OBJECT-TYPE
  SYNTAX       Integer32 (1..255)
  MAX-ACCESS   read-only
  STATUS       current
  DESCRIPTION
    "<Definition> Enumerated list of row entries that provide water level sensor data.
    <Parameter Type> status
    <Object Identifier> 1.3.6.1.4.1.1206.4.2.5.2.6.12.1.1"
::= { waterLevelSensorEntry 1 }

-- 5.8.21.2 Water Level Sensor Reading
waterLevelSensorReading OBJECT-TYPE
  SYNTAX       Integer32 (0..65535)
  UNITS        "centimeters"
  MAX-ACCESS   read-only
  STATUS       current
  DESCRIPTION
    "<Definition> Indicates the depth of the water from a user-defined point in centimeters. This may be used for stream depth, depth of water over a roadway for flooding, reservoir depth, or other such uses.
    <Format>
The value of 65535 shall indicate an error condition or missing value.
    <Parameter Type> status
    <Object Identifier> 1.3.6.1.4.1.1206.4.2.5.2.6.12.1.2"
::= { waterLevelSensorEntry 2 }

-- 5.8.21.3 Water Level Sensor Warning Level
waterLevelSensorWarningLevel OBJECT-TYPE
  SYNTAX       Integer32 (0..65535)
  UNITS        "centimeters"
  MAX-ACCESS   read-write
  STATUS       current
  DESCRIPTION
    "<Definition> Indicates the depth of the water from a user defined point in centimeters, that the water level is of concern. 
    <Format>
The value of 65535 shall indicate an error condition or missing value.
    <Parameter Type> configuration
    <Object Identifier> 1.3.6.1.4.1.1206.4.2.5.2.6.12.1.3"
::= { waterLevelSensorEntry 3 }

-- 5.8.21.4 Water Level Sensor Height
-- This object has been deprecated.
waterLevelSensorHeight OBJECT-TYPE
  SYNTAX       Integer32 (-1000..1001)
  UNITS        "meters"
  MAX-ACCESS   read-write
  STATUS       deprecated
  DESCRIPTION
    "<Definition> The height of the water level sensor with respect to the essReferenceHeight in meters.
    <Format>
The value of 1001 shall indicate a missing value.
    <Parameter Type> configuration
    <Superseded by> waterLevelSensorZOffset
    <Informative> This object was deprecated in version 05. 
    <Object Identifier> 1.3.6.1.4.1.1206.4.2.5.2.6.12.1.4"
::= { waterLevelSensorEntry 4 }

-- 5.8.21.5 Water Level Sensor Latitude
-- This object has been deprecated.
waterLevelSensorLatitude OBJECT-TYPE
  SYNTAX       Integer32 (-90000000..90000001)
  UNITS        "microdegrees latitude"
  MAX-ACCESS   read-write
  STATUS       deprecated
  DESCRIPTION
    "<Definition> The latitude in 10^-6 degrees of the ESS water level sensor, per WGS-84 datum.
    <Format>
The waterLevelSensorLatitude at the North Pole is 90,000,000. The waterLevelSensorLatitude at the South Pole is -90,000,000. The value 90,000,001 shall indicate a missing value.
    <Parameter Type> configuration
    <Superseded by> waterLevelSensorYOffset
    <Informative> This object was deprecated in version 05. 
    <Object Identifier> 1.3.6.1.4.1.1206.4.2.5.2.6.12.1.5"
  REFERENCE    "Resolution based on on-going location referencing activities; the WMO Binary Code Form FM 94 BUFR Table B item 0 05 001 can be obtained by dividing this value by 10."
::= { waterLevelSensorEntry 5 }

-- 5.8.21.6 Water Level Sensor Longitude
-- This object has been deprecated.
waterLevelSensorLongitude OBJECT-TYPE
  SYNTAX       Integer32 (-180000000..180000001)
  UNITS        "microdegrees longitude"
  MAX-ACCESS   read-write
  STATUS       deprecated
  DESCRIPTION
    "<Definition> The east longitude in 10^-6 degrees from the Prime Meridian of the ESS water level sensor location. 
    <Format>
The waterLevelSensorLongitude of 180 degrees West shall be -180,000,000. The waterLevelSensorLongitude of 180 degrees East shall be 180,000,000. The value 180,000,001 shall indicate a missing value.
    <Parameter Type> configuration
    <Superseded by> waterLevelSensorYOffset
    <Informative> This object was deprecated in version 05. 
    <Object Identifier> 1.3.6.1.4.1.1206.4.2.5.2.6.12.1.6"
  REFERENCE    "Resolution based on on-going location referencing activities; the WMO Binary Code Form FM 94 BUFR Table B item 0 06 001 can be obtained by dividing this value by 10."
::= { waterLevelSensorEntry 6 }

-- 5.8.21.7 Water Level Sensor Location
waterLevelSensorLocation OBJECT-TYPE
  SYNTAX       SnmpAdminString
  MAX-ACCESS   read-write
  STATUS       current
  DESCRIPTION
    "<Definition> A textual string indicating the location of the water level sensor., including a description of the reference point that the water depth is measured against.
    <Parameter Type> configuration
    <Object Identifier> 1.3.6.1.4.1.1206.4.2.5.2.6.12.1.7"
::= { waterLevelSensorEntry 7 }

-- 5.8.21.8 Water Level Sensor Model Information
-- This object has been deprecated.
waterLevelSensorModelInformation OBJECT-TYPE
  SYNTAX       Integer32 (0..255)
  MAX-ACCESS   read-write
  STATUS       deprecated
  DESCRIPTION
    "<Definition> Indicates the row in the Module Table (See NTCIP 1201) that contains information about the make, model, and version number of the sensor associated with this row of the Water Level Sensor Table.
    <Format>
The value of zero indicates that this information is not available.
    <Parameter Type> configuration
    <Supplanted by> waterLevelSensorEntityID
    <Informative> This object was deprecated in version 05.
    <Object Identifier> 1.3.6.1.4.1.1206.4.2.5.2.6.12.1.8"
::= { waterLevelSensorEntry 8 }

-- 5.8.21.9 Water Level Sensor Reference Point
waterLevelSensorReferencePoint OBJECT-TYPE
  SYNTAX       SnmpAdminString
  MAX-ACCESS   read-write
  STATUS       current
  DESCRIPTION
    "<Definition> A textual string describing the location of the reference point that the water depth is measured against.
    <Parameter Type> configuration
    <Object Identifier> 1.3.6.1.4.1.1206.4.2.5.2.6.12.1.9"
::= { waterLevelSensorEntry 9 }

-- 5.8.21.10 Water Level Sensor X Offset
waterLevelSensorXOffset OBJECT-TYPE
  SYNTAX       ITSInteger16
  UNITS        "centimeters"
  MAX-ACCESS   read-write
  STATUS       current
  DESCRIPTION
    "<Definition> The X offset of the water level sensor from the field device's reference location as defined by fdConfiguredLatitude and fdConfiguredLongitude. 
    <Format>
For stationary devices, the X offset shall indicate the eastward (positive) or westward (negative) distance from the reference location. For transportable and mobile devices, the X offset shall indicate distances to the starboard side (positive) or port side (negative) of the reference location on the vehicle.
    <Parameter Type> configuration
    <Object Identifier> 1.3.6.1.4.1.1206.4.2.5.2.5.2.1.10"
::= { waterLevelSensorEntry 10 }

-- 5.8.21.11 Water Level Sensor Y Offset
waterLevelSensorYOffset OBJECT-TYPE
  SYNTAX       ITSInteger16
  UNITS        "centimeters"
  MAX-ACCESS   read-write
  STATUS       current
  DESCRIPTION
    "<Definition> The Y offset of the water level sensor from the field device's reference location as defined by fdConfiguredLatitude and fdConfiguredLongitude. 
    <Format>
For stationary devices, the Y offset shall indicate the northward (positive) or southward (negative) distance from the reference location. For transportable and mobile devices, the Y offset shall indicate distances to the fore (positive) or aft (negative) of the reference location on the vehicle.
    <Parameter Type> configuration
    <Object Identifier> 1.3.6.1.4.1.1206.4.2.5.2.5.2.1.11"
::= { waterLevelSensorEntry 11 }

-- 5.8.21.12 Water Level Sensor Z Offset
waterLevelSensorZOffset OBJECT-TYPE
  SYNTAX       ITSInteger16
  UNITS        "centimeters"
  MAX-ACCESS   read-write
  STATUS       current
  DESCRIPTION
    "<Definition> The offset elevation of the water level sensor from the fdConfiguredElevation in centimeters.
    <Format>
Upward offsets shall be positive and downward offsets shall be negative. 
    <Parameter Type> configuration
    <Object Identifier> 1.3.6.1.4.1.1206.4.2.5.2.5.2.1.12"
::= { waterLevelSensorEntry 12 }

-- 5.8.21.13 Water Level Sensor Entity Identifier
waterLevelSensorEntityID OBJECT-TYPE
  SYNTAX       PhysicalIndexOrZero
  MAX-ACCESS   read-only
  STATUS       current
  DESCRIPTION
    "<Definition> Indicates the row in the entPhysicalTable (See RFC 4133) that contains information about the sensor, such as the manufacturer, model, and hardware and software revision identifiers. 
    <Format>
The value of zero indicates that this information is not available.
    <Parameter Type> status
    <Informative> The mechanism used to configure this value when adding or modifying a sensor is not defined by this document and is considered manufacturer-specific.
    <Object Identifier> 1.3.6.1.4.1.1206.4.2.5.2.6.12.1.13"
::= { waterLevelSensorEntry 13 }

-- 5.8.22 Number of Precipitation Sensors
precipitationSensorTableNumSensors OBJECT-TYPE
  SYNTAX       Integer32 (0..255)
  UNITS        "sensors"
  MAX-ACCESS   read-only
  STATUS       current
  DESCRIPTION
    "<Definition> Indicates the number of entries in the precipitation sensor table.
    <Parameter Type> status
    <Informative> This value may automatically change upon connecting or disconnecting a sensor; however, the table is still defined as a static table since the creation/deletion of rows is not managed through SNMP logic.
    <Object Identifier> 1.3.6.1.4.1.1206.4.2.5.2.6.13"
::= { essNtcipPrecip 13 }

-- 5.8.23 Precipitation Sensor Table
precipitationSensorTable OBJECT-TYPE
  SYNTAX       SEQUENCE OF PrecipitationSensorEntry
  MAX-ACCESS   not-accessible
  STATUS       current
  DESCRIPTION
    "<Definition> Table containing the precipitation sensor data fields.
    <Object Identifier> 1.3.6.1.4.1.1206.4.2.5.2.6.14"
::= { essNtcipPrecip 14 }

-- 5.8.24 Precipitation Sensor
precipitationSensorEntry OBJECT-TYPE
  SYNTAX       PrecipitationSensorEntry
  MAX-ACCESS   not-accessible
  STATUS       current
  DESCRIPTION
    "<Definition> Parameters for a specific precipitation sensor as described through a number of attributes as indicated by the following subclauses."
  INDEX { precipitationSensorIndex }
::= { precipitationSensorTable 1 }

PrecipitationSensorEntry ::= SEQUENCE {  
    precipitationSensorIndex                     Integer32,
    precipitationSensorHeight                    Integer32,
    precipitationSensorLatitude                  Integer32,
    precipitationSensorLongitude                 Integer32,
    precipitationSensorLocation                  SnmpAdminString,
    precipitationSensorModelInformationV4        Integer32,
    precipitationSensorPeriod                    Integer32,
    precipitationSensorAdjacentSnowDepth         Integer32,
    precipitationSensorRoadwaySnowDepth          Integer32,
    precipitationSensorRoadwaySnowPackDepth      Integer32,
    precipitationSensorPrecipYesNo               INTEGER,
    precipitationSensorPrecipRate                Integer32,
    precipitationSensorSnowfallAccumRate         Integer32,
    precipitationSensorPrecipSituation           INTEGER,
    precipitationSensorIceThickness              Integer32,
    precipitationSensorPrecipitationStartTime    Unsigned32,
    precipitationSensorPrecipitationEndTime      Unsigned32,
    precipitationSensorPrecipitationOneHour      Integer32,
    precipitationSensorPrecipitationThreeHours   Integer32,
    precipitationSensorPrecipitationSixHours     Integer32,
    precipitationSensorPrecipitationTwelveHours  Integer32,
    precipitationSensorPrecipitation24Hours      Integer32,
    precipitationSensorPrecipitationUserDefined  Integer32,
    precipitationSensorPrecipStartTimeV5         ITSTimeStamp,
    precipitationSensorPrecipEndTimeV5           ITSTimeStamp,
    precipitationSensorXOffset                   ITSInteger16,
    precipitationSensorYOffset                   ITSInteger16,
    precipitationSensorZOffset                   ITSInteger16,
    precipitationSensorEntityID                  PhysicalIndexOrZero }

-- 5.8.24.1 Precipitation Sensor Index
precipitationSensorIndex OBJECT-TYPE
  SYNTAX       Integer32 (1..255)
  MAX-ACCESS   read-only
  STATUS       current
  DESCRIPTION
    "<Definition> Enumerated list of row entries that provide precipitation sensor data.
    <Parameter Type> status
    <Object Identifier> 1.3.6.1.4.1.1206.4.2.5.2.6.14.1.1"
::= { precipitationSensorEntry 1 }

-- 5.8.24.2 Precipitation Sensor Height
-- This object has been deprecated.
precipitationSensorHeight OBJECT-TYPE
  SYNTAX       Integer32 (-1000..1001)
  UNITS        "meters"
  MAX-ACCESS   read-write
  STATUS       deprecated
  DESCRIPTION
    "<Definition> The height of the precipitation sensor with respect to the essReferenceHeight in meters. 
    <Format>
The value of 1001 shall indicate a missing value.
    <Parameter Type> configuration
    <Superseded by> precipitationSensorZOffset
    <Informative> This object was deprecated in version 05. 
    <Object Identifier> 1.3.6.1.4.1.1206.4.2.5.2.6.14.1.2"
  REFERENCE    "essReferenceHeight plus this value equals the WMO Binary Code Form FM 94 BUFR Table B item 0 07 001."
::= { precipitationSensorEntry 2 }

-- 5.8.24.3 Precipitation Sensor Latitude
-- This object has been deprecated.
precipitationSensorLatitude OBJECT-TYPE
  SYNTAX       Integer32 (-90000000..90000001)
  UNITS        "microdegrees latitude"
  MAX-ACCESS   read-write
  STATUS       deprecated
  DESCRIPTION
    "<Definition> The latitude in 10^-6 degrees of the ESS precipitation sensor, per WGS-84 datum. 
    <Format>
The precipitationSensorLatitude at the North Pole is 90,000,000. The precipitationSensorLatitude at the South Pole is -90,000,000. The value 90,000,001 shall indicate a missing value.
    <Parameter Type> configuration
    <Superseded by> precipitationSensorYOffset
    <Informative> This object was deprecated in version 05. 
    <Object Identifier> 1.3.6.1.4.1.1206.4.2.5.2.6.14.1.3"
  REFERENCE    "Resolution based on on-going location referencing activities; the WMO Binary Code Form FM 94 BUFR Table B item 0 05 001 can be obtained by dividing this value by 10."
::= { precipitationSensorEntry 3 }

-- 5.8.24.4 Precipitation Sensor Longitude
-- This object has been deprecated.
precipitationSensorLongitude OBJECT-TYPE
  SYNTAX       Integer32 (-180000000..180000001)
  UNITS        "microdegrees longitude"
  MAX-ACCESS   read-write
  STATUS       deprecated
  DESCRIPTION
    "<Definition> The east longitude in 10^-6 degrees from the Prime Meridian of the ESS precipitation sensor location. 
    <Format>
The precipitationSensorLongitude of 180 degrees West shall be -180,000,000. The precipitationSensorLongitude of 180 degrees East shall be 180,000,000. The value 180,000,001 shall indicate a missing value.
    <Parameter Type> configuration
    <Superseded by> precipitationSensorXOffset
    <Informative> This object was deprecated in version 05. 
    <Object Identifier> 1.3.6.1.4.1.1206.4.2.5.2.6.14.1.4"
  REFERENCE    "Resolution based on on-going location referencing activities; the WMO Binary Code Form FM 94 BUFR Table B item 0 06 001 can be obtained by dividing this value by 10."
::= { precipitationSensorEntry 4 }

-- 5.8.24.5 Precipitation Sensor Location
precipitationSensorLocation OBJECT-TYPE
  SYNTAX       SnmpAdminString
  MAX-ACCESS   read-write
  STATUS       current
  DESCRIPTION
    "<Definition> A textual string indicating the location of the precipitation sensor.
    <Parameter Type> configuration
    <Object Identifier> 1.3.6.1.4.1.1206.4.2.5.2.6.14.1.5"
::= { precipitationSensorEntry 5 }

-- 5.8.24.6 Precipitation Sensor Model Information Version 4
-- This object has been deprecated.
precipitationSensorModelInformationV4 OBJECT-TYPE
  SYNTAX       Integer32 (0..255)
  MAX-ACCESS   read-write
  STATUS       deprecated
  DESCRIPTION
    "<Definition> A reference to the row in the Module Table (See NTCIP 1201) that indicates the manufacturer, model, and version number of the precipitation sensor.
    <Format>
The value of zero indicates that this information is not available.
    <Parameter Type> configuration
    <Supplanted by> precipitationSensorEntityID
    <Informative> This object was deprecated in version 05. 
    <Object Identifier> 1.3.6.1.4.1.1206.4.2.5.2.6.14.1.6"
::= { precipitationSensorEntry 6 }

-- 5.8.24.7 Total Precipitation Period
precipitationSensorPeriod OBJECT-TYPE
  SYNTAX       Integer32 (0..86400)
  UNITS        "seconds"
  MAX-ACCESS   read-write
  STATUS       current
  DESCRIPTION
    "<Definition> The period, in seconds, that corresponds to the length of time that the total water equivalent is measured in precipitationSensorPrecipitationUserDefined.
    <Parameter Type> configuration
    <Object Identifier> 1.3.6.1.4.1.1206.4.2.5.2.6.14.1.7"
::= { precipitationSensorEntry 7 }

-- 5.8.24.8 Adjacent Snow Depth
precipitationSensorAdjacentSnowDepth OBJECT-TYPE
  SYNTAX       Integer32 (0..3001)
  UNITS        "centimeters"
  MAX-ACCESS   read-only
  STATUS       current
  DESCRIPTION
    "<Definition> The depth of snow in centimeters on representative areas other than the highway pavement, avoiding drifts and plowed areas. 
    <Format>
The value 3001 shall indicate an error condition or missing value.
    <Parameter Type> status
    <Object Identifier> 1.3.6.1.4.1.1206.4.2.5.2.6.14.1.8"
::= { precipitationSensorEntry 8 }

-- 5.8.24.9 Roadway Snow Depth
precipitationSensorRoadwaySnowDepth OBJECT-TYPE
  SYNTAX       Integer32 (0..3001)
  UNITS        "centimeters"
  MAX-ACCESS   read-only
  STATUS       current
  DESCRIPTION
    "<Definition> The current depth of unpacked snow in centimeters on the driving surface.
    <Format>
The value 3001 shall indicate an error condition or missing value.
    <Parameter Type> status
    <Object Identifier> 1.3.6.1.4.1.1206.4.2.5.2.6.14.1.9"
::= { precipitationSensorEntry 9 }

-- 5.8.24.10 Roadway Snow Pack Depth
precipitationSensorRoadwaySnowPackDepth OBJECT-TYPE
  SYNTAX       Integer32 (0..3001)
  UNITS        "centimeters"
  MAX-ACCESS   read-only
  STATUS       current
  DESCRIPTION
    "<Definition> The current depth of packed snow in centimeters on the roadway surface.
    <Format>
The value 3001 shall indicate an error condition or missing value.
    <Parameter Type> status
    <Object Identifier> 1.3.6.1.4.1.1206.4.2.5.2.6.14.1.10"
::= { precipitationSensorEntry 10 }

-- 5.8.24.11 Precipitation Indicator
precipitationSensorPrecipYesNo OBJECT-TYPE
  SYNTAX       INTEGER {
    precip (1),
    noPrecip (2),
    error (3) }
  MAX-ACCESS   read-only
  STATUS       current
  DESCRIPTION
    "<Definition> Indicates whether or not moisture is detected by the sensor.
    <Format>
precip - Moisture is currently being detected by the precipitation sensor. 
    0.01 inches of liquid water equivalent is to be detected.
noPrecip - Moisture is not currently being detected by the precipitation 
    sensor
error - The sensor is either not connected, not reporting, or is 
    indicating an error
    <Parameter Type> status
    <Object Identifier> 1.3.6.1.4.1.1206.4.2.5.2.6.14.1.11"
::= { precipitationSensorEntry 11 }

-- 5.8.24.12 Rainfall or Water Equivalent of Snow
precipitationSensorPrecipRate OBJECT-TYPE
  SYNTAX       Integer32 (0..65535)
  UNITS        "tenths of grams per square meter per second"
  MAX-ACCESS   read-only
  STATUS       current
  DESCRIPTION
    "<Definition> The rainfall, or water equivalent of snow, rate in tenths of grams per square meter per second (for rain, this is approximately to 0.36 mm/hr). 
    <Format>
The value of 65535 shall indicate an error condition or missing value.
    <Parameter Type> status
    <Object Identifier> 1.3.6.1.4.1.1206.4.2.5.2.6.14.1.12"
  REFERENCE    "WMO Binary Code Form FM 94 BUFR Table B item 0 13 014."
::= { precipitationSensorEntry 12 }

-- 5.8.24.13 Snowfall Accumulation Rate
precipitationSensorSnowfallAccumRate OBJECT-TYPE
  SYNTAX       Integer32 (0..65535)
  UNITS        "10^-7 meters per second"
  MAX-ACCESS   read-only
  STATUS       current
  DESCRIPTION
    "<Definition> The snowfall accumulation rate in 10^-7 meters per second (this is equivalent to 0.36 mm/hr). 
    <Format>
The value 65535 shall indicate an error condition or missing value.
    <Parameter Type> status
    <Object Identifier> 1.3.6.1.4.1.1206.4.2.5.2.6.14.1.13"
  REFERENCE    "WMO Binary Code Form FM 94 BUFR Table B item 0 13 015."
::= { precipitationSensorEntry 13 }

-- 5.8.24.14 Precipitation Situation
precipitationSensorPrecipSituation OBJECT-TYPE
  SYNTAX       INTEGER {
    other (1),
    unknown (2),
    noPrecipitation (3),
    unidentifiedSlight (4),
    unidentifiedModerate (5),
    unidentifiedHeavy (6),
    snowSlight (7),
    snowModerate (8),
    snowHeavy (9),
    rainSlight (10),
    rainModerate (11),
    rainHeavy (12),
    frozenPrecipitationSlight (13),
    frozenPrecipitationModerate (14),
    frozenPrecipitationHeavy (15) }
  MAX-ACCESS   read-only
  STATUS       current
  DESCRIPTION
    "<Definition> Describes the weather situation in terms of precipitation. For automated stations, describes the intensity and precipitation type as specified in the first row of the precipitationSensorTable.
    <Format>
Intensity     Meaning 
slight      < 2mm/h water equivalent 
moderate    >= 2 and < 8 mm/h water equivalent 
heavy       >= 8 mm/h water equivalent If one exists, the corresponding 
            BUFR value is indicated for staffed (BUFRs) and automated 
            (BUFRa) stations. The indicated value can be found in the 
            BUFR Table referenced below. Defined values are: 

Range   BUFRa   BUFRs  Meaning 
1                      other 
2                      unknown  
3                      no precipitation 
4                      unidentified slight 
5                      unidentified moderate 
6                      unidentified heavy 
7       171      85    snow slight 
8       172      86    snow moderate 
9       173      86    snow heavy 
10               61    rain slight 
11      165      63    rain moderate 
12      163      65    rain heavy 
13                     frozen precipitation slight 
14                     frozen precipitation moderate 
15                     frozen precipitation heavy
    <Parameter Type> status
    <Object Identifier> 1.3.6.1.4.1.1206.4.2.5.2.6.14.1.14"
  REFERENCE    "The values identified in the above table for BUFRa and BUFRs can be found in WMO Binary Code Form FM 94 BUFR Table B item 0 20 003."
::= { precipitationSensorEntry 14 }

-- 5.8.24.15 Ice Deposit (Thickness)
-- This object has been deprecated.
precipitationSensorIceThickness OBJECT-TYPE
  SYNTAX       Integer32 (0..65535)
  UNITS        "millimeters"
  MAX-ACCESS   read-only
  STATUS       deprecated
  DESCRIPTION
    "<Definition> Indicates the thickness of the ice in millimeters.
    <Format>
The value 65535 shall indicate an error condition or missing value.
    <Parameter Type> status
    <Superseded by> essSurfaceIceOrWaterDepth
    <Informative> This object was deprecated in v05 because the thickness of ice can vary by location, especially with the addition of chemicals. As such, the superseding object is associated with a pavement sensor rather than a precipitation sensor.
    <Object Identifier> 1.3.6.1.4.1.1206.4.2.5.2.6.14.1.15"
::= { precipitationSensorEntry 15 }

-- 5.8.24.16 Precipitation Start Time
-- This object has been deprecated.
precipitationSensorPrecipitationStartTime OBJECT-TYPE
  SYNTAX       Unsigned32
  UNITS        "seconds"
  MAX-ACCESS   read-only
  STATUS       deprecated
  DESCRIPTION
    "<Definition> The time at which the most recent precipitation event began, measured in seconds since 00:00:00 January 1, 1970 UTC. The precipitation event begins when 0.01 inches of liquid water equivalent is detected.
    <Format>
As this standard has been developed long after 1970, a value of 0 for time should indicate to the management station that the data received is suspect.
    <Parameter Type> status
    <Superseded by> precipitationSensorPrecipStartDate  and precipitationSensorPrecipStartTimeV5 
    <Informative> This object was deprecated in version 05. 
    <Object Identifier> 1.3.6.1.4.1.1206.4.2.5.2.6.14.1.16"
::= { precipitationSensorEntry 16 }

-- 5.8.24.17 Precipitation End Time
-- This object has been deprecated.
precipitationSensorPrecipitationEndTime OBJECT-TYPE
  SYNTAX       Unsigned32
  UNITS        "seconds"
  MAX-ACCESS   read-only
  STATUS       deprecated
  DESCRIPTION
    "<Definition> The time at which the most recently completed precipitation event ended, measured in seconds since 00:00:00 January 1, 1970 UTC. 
    <Format>
As this standard has been developed long after 1970, a value of 0 for the time should indicate to the management station that the data received is suspect.
    <Parameter Type> status
    <Superseded by> precipitationSensorPrecipEndDate  and precipitationSensorPrecipEndTimeV5 
    <Informative> This object was deprecated in version 05. 
    <Object Identifier> 1.3.6.1.4.1.1206.4.2.5.2.6.14.1.17"
::= { precipitationSensorEntry 17 }

-- 5.8.24.18 Total Precipitation Past One Hour
precipitationSensorPrecipitationOneHour OBJECT-TYPE
  SYNTAX       Integer32 (0..65535)
  UNITS        "tenths of kilograms per square meter"
  MAX-ACCESS   read-only
  STATUS       current
  DESCRIPTION
    "<Definition> The total water equivalent precipitation over the hour preceding the observation in tenths of kilograms per square meter (for rain, this is approximately tenths of millimeters). 
    <Format>
The value of 65535 shall indicate an error condition or missing value.
    <Parameter Type> status
    <Object Identifier> 1.3.6.1.4.1.1206.4.2.5.2.6.14.1.18"
  REFERENCE    "WMO Binary Code Form FM 94 BUFR Table B item 0 13 019."
::= { precipitationSensorEntry 18 }

-- 5.8.24.19 Total Precipitation Past Three Hours
precipitationSensorPrecipitationThreeHours OBJECT-TYPE
  SYNTAX       Integer32 (0..65535)
  UNITS        "tenths of kilograms per square meter"
  MAX-ACCESS   read-only
  STATUS       current
  DESCRIPTION
    "<Definition> The total water equivalent precipitation over the three hours preceding the observation in tenths of kilograms per square meter (for rain, this is approximately tenths of millimeters). 
    <Format>
The value of 65535 shall indicate an error condition or missing value.
    <Parameter Type> status
    <Object Identifier> 1.3.6.1.4.1.1206.4.2.5.2.6.14.1.19"
  REFERENCE    "WMO Binary Code Form FM 94 BUFR Table B item 0 13 020."
::= { precipitationSensorEntry 19 }

-- 5.8.24.20 Total Precipitation Past Six Hours
precipitationSensorPrecipitationSixHours OBJECT-TYPE
  SYNTAX       Integer32 (0..65535)
  UNITS        "tenths of kilograms per square meter"
  MAX-ACCESS   read-only
  STATUS       current
  DESCRIPTION
    "<Definition> The total water equivalent precipitation over the six hours preceding the observation in tenths of kilograms per square meter (for rain, this is approximately tenths of millimeters). 
    <Format>
The value of 65535 shall indicate an error condition or missing value.
    <Parameter Type> status
    <Object Identifier> 1.3.6.1.4.1.1206.4.2.5.2.6.14.1.20"
  REFERENCE    "WMO Binary Code Form FM 94 BUFR Table B item 0 13 021."
::= { precipitationSensorEntry 20 }

-- 5.8.24.21 Total Precipitation Past Twelve Hours
precipitationSensorPrecipitationTwelveHours OBJECT-TYPE
  SYNTAX       Integer32 (0..65535)
  UNITS        "tenths of kilograms per square meter"
  MAX-ACCESS   read-only
  STATUS       current
  DESCRIPTION
    "<Definition> The total water equivalent precipitation over the twelve hours preceding the observation in tenths of kilograms per square meter (for rain, this is approximately to tenths of millimeters). 
    <Format>
The value of 65535 shall indicate an error condition or missing value.
    <Parameter Type> status
    <Object Identifier> 1.3.6.1.4.1.1206.4.2.5.2.6.14.1.21"
  REFERENCE    "WMO Binary Code Form FM 94 BUFR Table B item 0 13 022."
::= { precipitationSensorEntry 21 }

-- 5.8.24.22 Total Precipitation Past Twenty-Four Hours
precipitationSensorPrecipitation24Hours OBJECT-TYPE
  SYNTAX       Integer32 (0..65535)
  UNITS        "tenths of kilograms per square meter"
  MAX-ACCESS   read-only
  STATUS       current
  DESCRIPTION
    "<Definition> The total water equivalent precipitation over the twenty-four hours preceding the observation in tenths of kilograms per square meter (for rain, this is equivalent to tenths of millimeters). 
    <Format>
The value of 65535 shall indicate an error condition or missing value.
    <Parameter Type> status
    <Object Identifier> 1.3.6.1.4.1.1206.4.2.5.2.6.14.1.22"
  REFERENCE    "WMO Binary Code Form FM 94 BUFR Table B item 0 13 023."
::= { precipitationSensorEntry 22 }

-- 5.8.24.23 Total Precipitation User Defined Period
precipitationSensorPrecipitationUserDefined OBJECT-TYPE
  SYNTAX       Integer32 (0..65535)
  UNITS        "tenths of kilograms per square meter"
  MAX-ACCESS   read-only
  STATUS       current
  DESCRIPTION
    "<Definition> The total water equivalent precipitation over the precipitationSensorPeriod preceding the observation in tenths of kilograms per square meter (for rain, this is equivalent to tenths of millimeters). 
    <Format>
The value of 65535 shall indicate an error condition or missing value.
    <Parameter Type> status
    <Object Identifier> 1.3.6.1.4.1.1206.4.2.5.2.6.14.1.23"
::= { precipitationSensorEntry 23 }

-- 5.8.24.24 Precipitation Start Time Version 05
precipitationSensorPrecipStartTimeV5 OBJECT-TYPE
  SYNTAX       ITSTimeStamp
  MAX-ACCESS   read-only
  STATUS       current
  DESCRIPTION
    "<Definition> The UTC time at which the most recent precipitation event began on the precipitationSensorPrecipStartDate. The precipitation event begins when 0.254 mm of liquid water equivalent is detected.
    <Parameter Type> status
    <Object Identifier> 1.3.6.1.4.1.1206.4.2.5.2.6.14.1.25"
  DEFVAL { '0000000000000000'H }
::= { precipitationSensorEntry 25 }

-- 5.8.24.25 Precipitation End Time Version 05
precipitationSensorPrecipEndTimeV5 OBJECT-TYPE
  SYNTAX       ITSTimeStamp
  MAX-ACCESS   read-only
  STATUS       current
  DESCRIPTION
    "<Definition> The UTC time at which the most recently completed precipitation event ended on the precipitationSensorPrecipEndDate. 
    <Parameter Type> status
    <Object Identifier> 1.3.6.1.4.1.1206.4.2.5.2.6.14.1.27"
  DEFVAL { '0000000000000000'H }
::= { precipitationSensorEntry 27 }

-- 5.8.24.26 Precipitation Sensor X Offset
precipitationSensorXOffset OBJECT-TYPE
  SYNTAX       ITSInteger16
  UNITS        "centimeters"
  MAX-ACCESS   read-write
  STATUS       current
  DESCRIPTION
    "<Definition> The X offset of the precipitation sensor from the field device's reference location as defined by fdConfiguredLatitude and fdConfiguredLongitude. 
    <Format>
For stationary devices, the X offset shall indicate the eastward (positive) or westward (negative) distance from the reference location. For transportable and mobile devices, the X offset shall indicate distances to the starboard side (positive) or port side (negative) of the reference location on the vehicle.
    <Parameter Type> configuration
    <Object Identifier> 1.3.6.1.4.1.1206.4.2.5.2.6.14.1.28"
::= { precipitationSensorEntry 28 }

-- 5.8.24.27 Precipitation Sensor Y Offset
precipitationSensorYOffset OBJECT-TYPE
  SYNTAX       ITSInteger16
  UNITS        "centimeters"
  MAX-ACCESS   read-write
  STATUS       current
  DESCRIPTION
    "<Definition> The Y offset of the precipitation sensor from the field device's reference location as defined by fdConfiguredLatitude and fdConfiguredLongitude. 
    <Format>
For stationary devices, the Y offset shall indicate the northward (positive) or southward (negative) distance from the reference location. For transportable and mobile devices, the Y offset shall indicate distances to the fore (positive) or aft (negative) of the reference location on the vehicle.
    <Parameter Type> configuration
    <Object Identifier> 1.3.6.1.4.1.1206.4.2.5.2.6.14.1.29"
::= { precipitationSensorEntry 29 }

-- 5.8.24.28 Precipitation Sensor Z Offset
precipitationSensorZOffset OBJECT-TYPE
  SYNTAX       ITSInteger16
  UNITS        "centimeters"
  MAX-ACCESS   read-write
  STATUS       current
  DESCRIPTION
    "<Definition> The offset elevation of the precipitation sensor from the fdConfiguredElevation in centimeters.
    <Format>
Upward offsets shall be positive and downward offsets shall be negative. 
    <Parameter Type> configuration
    <Object Identifier> 1.3.6.1.4.1.1206.4.2.5.2.6.14.1.30"
::= { precipitationSensorEntry 30 }

-- 5.8.24.29 Precipitation Sensor Entity Identifier
precipitationSensorEntityID OBJECT-TYPE
  SYNTAX       PhysicalIndexOrZero
  MAX-ACCESS   read-only
  STATUS       current
  DESCRIPTION
    "<Definition> Indicates the row in the entPhysicalTable (See RFC 4133) that contains information about the sensor, such as the manufacturer, model, and hardware and software revision identifiers. 
    <Format>
The value of zero indicates that this information is not available.
    <Parameter Type> status
    <Informative> The mechanism used to configure this value when adding or modifying a sensor is not defined by this document and is considered manufacturer-specific.
    <Object Identifier> 1.3.6.1.4.1.1206.4.2.5.2.6.14.1.31"
::= { precipitationSensorEntry 31 }

-- 5.8.25 Number of Humidity Sensors
humiditySensorTableNumSensors OBJECT-TYPE
  SYNTAX       Integer32 (0..255)
  UNITS        "sensors"
  MAX-ACCESS   read-only
  STATUS       current
  DESCRIPTION
    "<Definition> Indicates the number of entries in the humidity sensor table.
    <Parameter Type> status
    <Informative> This value may automatically change upon connecting or disconnecting a sensor; however, the table is still defined as a static table since the creation/deletion of rows is not managed through SNMP logic.
    <Object Identifier> 1.3.6.1.4.1.1206.4.2.5.2.6.15"
::= { essNtcipPrecip 15 }

-- 5.8.26 Humidity Sensor Table
humiditySensorTable OBJECT-TYPE
  SYNTAX       SEQUENCE OF HumiditySensorEntry
  MAX-ACCESS   not-accessible
  STATUS       current
  DESCRIPTION
    "<Definition> Table containing the humidity sensor data.
    <Object Identifier> 1.3.6.1.4.1.1206.4.2.5.2.6.16"
::= { essNtcipPrecip 16 }

-- 5.8.27 Humidity Sensor
humiditySensorEntry OBJECT-TYPE
  SYNTAX       HumiditySensorEntry
  MAX-ACCESS   not-accessible
  STATUS       current
  DESCRIPTION
    "<Definition> A humidity sensor is a sensor that reports the relative humidity. It can be described through a number of attributes as indicated by the following subclauses."
  INDEX { humiditySensorIndex }
::= { humiditySensorTable 1 }

HumiditySensorEntry ::= SEQUENCE {
    humiditySensorIndex                   Integer32,
    humiditySensorHeight                  Integer32,
    humiditySensorLatitude                Integer32,
    humiditySensorLongitude               Integer32,
    humiditySensorLocation                SnmpAdminString,
    humiditySensorModelInformation        Integer32,
    humiditySensorRelativeHumidity        Integer32,
    humiditySensorTemperatureInformation  Integer32,
    humiditySensorWetbulbTemp             Integer32,
    humiditySensorDewpointTemp            Integer32,
    humiditySensorXOffset                 ITSInteger16,
    humiditySensorYOffset                 ITSInteger16,
    humiditySensorZOffset                 ITSInteger16,
    humiditySensorEntityID                PhysicalIndexOrZero}

-- 5.8.27.1 Humidity Sensor Index
humiditySensorIndex OBJECT-TYPE
  SYNTAX       Integer32 (1..255)
  MAX-ACCESS   read-only
  STATUS       current
  DESCRIPTION
    "<Definition> Enumerated list of row entries that provide humidity sensor data.
    <Parameter Type> status
    <Object Identifier> 1.3.6.1.4.1.1206.4.2.5.2.6.16.1.1"
::= { humiditySensorEntry 1 }

-- 5.8.27.2 Humidity Sensor Height
-- This object has been deprecated.
humiditySensorHeight OBJECT-TYPE
  SYNTAX       Integer32 (-1000..1001)
  UNITS        "meters"
  MAX-ACCESS   read-write
  STATUS       deprecated
  DESCRIPTION
    "<Definition> The height of the humidity sensor with respect to the essReferenceHeight in meters. 
    <Format>
The value of 1001 shall indicate a missing value.
    <Parameter Type> configuration
    <Superseded by> humiditySensorZOffset
    <Informative> This object was deprecated in version 05. 
    <Object Identifier> 1.3.6.1.4.1.1206.4.2.5.2.6.16.1.2"
  REFERENCE    "essReferenceHeight plus this value equals the WMO Binary Code Form FM 94 BUFR Table B item 0 07 001."
::= { humiditySensorEntry 2 }

-- 5.8.27.3 Humidity Sensor Latitude
-- This object has been deprecated.
humiditySensorLatitude OBJECT-TYPE
  SYNTAX       Integer32 (-90000000..90000001)
  UNITS        "microdegrees latitude"
  MAX-ACCESS   read-write
  STATUS       deprecated
  DESCRIPTION
    "<Definition> The latitude in 10^-6 degrees of the ESS humidity sensor, per WGS-84 datum. 
    <Format>
The humiditySensorLatitude at the North Pole is 90,000,000. The humiditySensorLatitude at the South Pole is -90,000,000. The value 90,000,001 shall indicate a missing value.
    <Parameter Type> configuration
    <Superseded by> humiditySensorYOffset
    <Informative> This object was deprecated in version 05. 
    <Object Identifier> 1.3.6.1.4.1.1206.4.2.5.2.6.16.1.3"
  REFERENCE    "Resolution based on on-going location referencing activities; the WMO Binary Code Form FM 94 BUFR Table B item 0 05 001 can be obtained by dividing this value by 10."
::= { humiditySensorEntry 3 }

-- 5.8.27.4 Humidity Sensor Longitude
-- This object has been deprecated.
humiditySensorLongitude OBJECT-TYPE
  SYNTAX       Integer32 (-180000000..180000001)
  UNITS        "microdegrees longitude"
  MAX-ACCESS   read-write
  STATUS       deprecated
  DESCRIPTION
    "<Definition> The east longitude in 10^-6 degrees from the Prime Meridian of the ESS humidity sensor location. 
    <Format>
The humiditySensorLongitude of 180 degrees West shall be -180,000,000. The humiditySensorLongitude of 180 degrees East shall be 180,000,000. The value 180,000,001 shall indicate a missing value.
    <Parameter Type> configuration
    <Superseded by> humiditySensorXOffset
    <Informative> This object was deprecated in version 05. 
    <Object Identifier> 1.3.6.1.4.1.1206.4.2.5.2.6.16.1.4"
  REFERENCE    "Resolution based on on-going location referencing activities; the WMO Binary Code Form FM 94 BUFR Table B item 0 06 001 can be obtained by dividing this value by 10."
::= { humiditySensorEntry 4 }

-- 5.8.27.5 Humidity Sensor Location
humiditySensorLocation OBJECT-TYPE
  SYNTAX       SnmpAdminString
  MAX-ACCESS   read-write
  STATUS       current
  DESCRIPTION
    "<Definition> A textual string indicating the location of the humidity sensor.
    <Parameter Type> configuration
    <Object Identifier> 1.3.6.1.4.1.1206.4.2.5.2.6.16.1.5"
::= { humiditySensorEntry 5 }

-- 5.8.27.6 Humidity Sensor Model Information
-- This object has been deprecated.
humiditySensorModelInformation OBJECT-TYPE
  SYNTAX       Integer32 (0..255)
  MAX-ACCESS   read-write
  STATUS       deprecated
  DESCRIPTION
    "<Definition> Indicates the row in the Module Table (See NTCIP 1201) that contains information about the make, model, and version number of the sensor associated with this row of the Humidity Sensor Table.
    <Format>
The value of zero indicates that this information is not available.
    <Parameter Type> configuration
    <Supplanted by> humiditySensorEntityID
    <Informative> This object was deprecated in version 05.
    <Object Identifier> 1.3.6.1.4.1.1206.4.2.5.2.6.16.1.6"
::= { humiditySensorEntry 6 }

-- 5.8.27.7 Relative Humidity
humiditySensorRelativeHumidity OBJECT-TYPE
  SYNTAX       Integer32 (0..101)
  UNITS        "percent humidity"
  MAX-ACCESS   read-only
  STATUS       current
  DESCRIPTION
    "<Definition> The relative humidity in percent.
    <Format>
The value of 101 shall indicate an error condition or missing value.
    <Parameter Type> status
    <Object Identifier> 1.3.6.1.4.1.1206.4.2.5.2.6.16.1.7"
  REFERENCE    "WMO Binary Code Form FM 94 BUFR Table B item 0 13 003."
::= { humiditySensorEntry 7 }

-- 5.8.27.8 Humidity Sensor Temperature Information
humiditySensorTemperatureInformation OBJECT-TYPE
  SYNTAX       Integer32 (0..255)
  MAX-ACCESS   read-write
  STATUS       current
  DESCRIPTION
    "<Definition> Indicates the row in the essTemperatureSensorTable that contains the temperature associated with this row of the Humidity Sensor Table. If a SetRequest-PDU attempts to set this object to a value that does not reference an existing EssTemperatureSensorEntry, the ESS shall respond with an inconsistentValue error. The ESS shall automatically update this value if the index of the referenced temp sensor changes (e.g., due to another temperature sensor being disconnected and the index numbers being updated).
    <Format>
The value of zero indicates that this information is not available.
    <Parameter Type> configuration
    <Object Identifier> 1.3.6.1.4.1.1206.4.2.5.2.6.16.1.8"
  DEFVAL {1}
::= { humiditySensorEntry 8 }

-- 5.8.27.9 Wetbulb Temperature
humiditySensorWetbulbTemp OBJECT-TYPE
  SYNTAX       Integer32 (-1000..1001)
  UNITS        "tenths of degrees Celsius"
  MAX-ACCESS   read-only
  STATUS       current
  DESCRIPTION
    "<Definition> The wet-bulb temperature in tenths of degrees Celsius for the row of the essTemperatureSensorTable as specified by humiditySensorTemperatureInformation for this humidity sensor. The temperature is an instantaneous reading.
    <Format>
The value 1001 shall indicate an error condition or missing value.
    <Parameter Type> status
    <Object Identifier> 1.3.6.1.4.1.1206.4.2.5.2.6.16.1.9"
  REFERENCE    "is based on WMO Binary Code Form FM 94 BUFR Table B item 0 12 002; temperature in Kelvin is determined by adding 273.15 to this value."
::= { humiditySensorEntry 9 }

-- 5.8.27.10 Dewpoint Temperature
humiditySensorDewpointTemp OBJECT-TYPE
  SYNTAX       Integer32 (-1000..1001)
  UNITS        "tenths of degrees Celsius"
  MAX-ACCESS   read-only
  STATUS       current
  DESCRIPTION
    "<Definition> The dewpoint temperature in tenths of degrees Celsius for the row of the essTemperatureSensorTable as specified by humiditySensorTemperatureInformation. The temperature is an instantaneous reading.
    <Format>
The value 1001 shall indicate an error condition or missing value.
    <Parameter Type> status
    <Object Identifier> 1.3.6.1.4.1.1206.4.2.5.2.6.16.1.10"
  REFERENCE    "Resolution is based on WMO Binary Code Form FM 94 BUFR Table B item 0 12 003; temperature in Kelvin is determined by adding 273.15 to this value."
::= { humiditySensorEntry 10 }

-- 5.8.27.11 Humidity Sensor X Offset
humiditySensorXOffset OBJECT-TYPE
  SYNTAX       ITSInteger16
  UNITS        "centimeters"
  MAX-ACCESS   read-write
  STATUS       current
  DESCRIPTION
    "<Definition> The X offset of the humidity sensor from the field device's reference location as defined by fdConfiguredLatitude and fdConfiguredLongitude. 
    <Format>
For stationary devices, the X offset shall indicate the eastward (positive) or westward (negative) distance from the reference location. For transportable and mobile devices, the X offset shall indicate distances to the starboard side (positive) or port side (negative) of the reference location on the vehicle.
    <Parameter Type> configuration
    <Object Identifier> 1.3.6.1.4.1.1206.4.2.5.2.6.16.1.11"
::= { humiditySensorEntry 11 }

-- 5.8.27.12 Humidity Sensor Y Offset
humiditySensorYOffset OBJECT-TYPE
  SYNTAX       ITSInteger16
  UNITS        "centimeters"
  MAX-ACCESS   read-write
  STATUS       current
  DESCRIPTION
    "<Definition> The Y offset of the humidity sensor from the field device's reference location as defined by fdConfiguredLatitude and fdConfiguredLongitude. 
    <Format>
For stationary devices, the Y offset shall indicate the northward (positive) or southward (negative) distance from the reference location. For transportable and mobile devices, the Y offset shall indicate distances to the fore (positive) or aft (negative) of the reference location on the vehicle.
    <Parameter Type> configuration
    <Object Identifier> 1.3.6.1.4.1.1206.4.2.5.2.6.16.1.12"
::= { humiditySensorEntry 12 }

-- 5.8.27.13 Humidity Sensor Z Offset
humiditySensorZOffset OBJECT-TYPE
  SYNTAX       ITSInteger16
  UNITS        "centimeters"
  MAX-ACCESS   read-write
  STATUS       current
  DESCRIPTION
    "<Definition> The offset elevation of the humidity sensor from the fdConfiguredElevation in centimeters.
    <Format>
Upward offsets shall be positive and downward offsets shall be negative. 
    <Parameter Type> configuration
    <Object Identifier> 1.3.6.1.4.1.1206.4.2.5.2.6.16.1.13"
::= { humiditySensorEntry 13 }

-- 5.8.27.14 Humidity Sensor Entity Identifier
humiditySensorEntityID OBJECT-TYPE
  SYNTAX       PhysicalIndexOrZero
  MAX-ACCESS   read-only
  STATUS       current
  DESCRIPTION
    "<Definition> Indicates the row in the entPhysicalTable (See RFC 4133) that contains information about the sensor, such as the manufacturer, model, and hardware and software revision identifiers. 
    <Format>
The value of zero indicates that this information is not available.
    <Parameter Type> status
    <Informative> The mechanism used to configure this value when adding or modifying a sensor is not defined by this document and is considered manufacturer-specific.
    <Object Identifier> 1.3.6.1.4.1.1206.4.2.5.2.6.16.1.14"
::= { humiditySensorEntry 14 }

-- 5.9 Radiation Objects
essBufrRadiation OBJECT-IDENTITY
    STATUS       current
  DESCRIPTION
    "<Definition> Objects used to describe the data that is collected by the pavement surface sensor and recorded in a format consistent with BUFR.
    <Object Identifier> 1.3.6.1.4.1.1206.4.2.5.1.14"
::= {essBufr 14 }

essNtcipRadiation OBJECT-IDENTITY
    STATUS       current
  DESCRIPTION
    "<Definition> Objects used to describe the data that is collected by the pavement surface sensor and recorded in a format not directly derived from BUFR.
    <Object Identifier> 1.3.6.1.4.1.1206.4.2.5.2.7"
::= {essNtcip 7}

-- 5.9.1 Solar Radiation
-- This object has been deprecated.
essSolarRadiation OBJECT-TYPE
  SYNTAX       Integer32 (0..65535)
  UNITS        "joules per square meter"
  MAX-ACCESS   read-only
  STATUS       deprecated
  DESCRIPTION
    "<Definition> The direct solar radiation integrated over the 24 hours preceding the observation in Joules per square meter. The value of 65535 shall indicate a missing value.
    <Parameter Type> status
    <Superseded by> essInstantaneousSolarRadiation
    <Informative> This object was deprecated in version 02. 
    <Object Identifier> 1.3.6.1.4.1.1206.4.2.5.1.14.24"
  REFERENCE    "WMO Code Form FM 94 BUFR Table B item 0 14 024."
::= { essBufrRadiation 24 }

-- 5.9.2 Total Sun
-- This object has been deprecated.
essTotalSun OBJECT-TYPE
  SYNTAX       Integer32 (0..1441)
  UNITS        "minutes"
  MAX-ACCESS   read-only
  STATUS       deprecated
  DESCRIPTION
    "<Definition> The total amount of sunshine in minutes over the 24 hour period preceding the observation. 
    <Format>
The value of 1441 shall indicate a missing value.
    <Parameter Type> status
    <Superseded by> essTotalSunV4
    <Informative> This object was deprecated in version 04. 
    <Object Identifier> 1.3.6.1.4.1.1206.4.2.5.1.14.31"
  REFERENCE    "WMO Code Form FM 94 BUFR Table B item 0 14 031."
::= { essBufrRadiation 31 }

-- 5.9.3 Cloud Cover Situation
-- This object has been deprecated.
essCloudSituation OBJECT-TYPE
  SYNTAX       INTEGER {
    overcast (1),
    cloudy (2),
    partlyCloudy (3),
    mostlyClear (4),
    clear (5) }
  MAX-ACCESS   read-only
  STATUS       deprecated
  DESCRIPTION
    "<Definition> Describes the amount of cloud cover. The associated percentages of cloud cover are indicated to identify the differences between the defined values.
    <Format>
Defined values are: 
Value Meaning        Percent Cloud Cover
1     Overcast       100%
2     Mostly cloudy  62.5%-99%
3     Partly cloudy  37.5%-62.4%
4     Mostly sunny   1%-37.4%
5     Clear skies    0%
    <Parameter Type> status
    <Superseded by> essCloudSituationV4
    <Informative> This object was deprecated in version 04. 
    <Object Identifier> 1.3.6.1.4.1.1206.4.2.5.2.7.1"
::= { essNtcipRadiation 1 }

-- 5.9.4 Terrestrial Radiation
-- This object has been deprecated.
essInstantaneousTerrestrialRadiation OBJECT-TYPE
  SYNTAX       Integer32 (-2048..2049)
  UNITS        "watts per square meter"
  MAX-ACCESS   read-only
  STATUS       deprecated
  DESCRIPTION
    "<Definition> The instantaneous infrared (wavelength of 3.5 - 50 micrometers) radiation being emitted from the atmosphere in watts per square meter. 
    <Format>
The value of 2049 shall indicate a missing value.
    <Parameter Type> status
    <Superseded by> essInstantaneousTerrestrialRadiationV4
    <Informative> This object was deprecated in version 04. 
    <Object Identifier> 1.3.6.1.4.1.1206.4.2.5.1.14.17"
  REFERENCE    "WMO Code Form FM 94 BUFR Table B item 0 14 017"
::= { essBufrRadiation 17 }

-- 5.9.5 Solar Radiation—Version 2
-- This object has been deprecated.
essInstantaneousSolarRadiation OBJECT-TYPE
  SYNTAX       Integer32 (-2048..2049)
  UNITS        "watts per square meter"
  MAX-ACCESS   read-only
  STATUS       deprecated
  DESCRIPTION
    "<Definition> The instantaneous ultraviolet, visible, and near-infrared (wavelength of less than 3.0 micrometers) radiation hitting the earth's surface in watts per square meter. 
    <Format>
The value of 2049 shall indicate a missing value.
    <Parameter Type> status
    <Superseded by> essInstantaneousSolarRadiationV4
    <Informative> This object was deprecated in version 04. 
    <Object Identifier> 1.3.6.1.4.1.1206.4.2.5.1.14.18"
  REFERENCE    "WMO Code Form FM 94 BUFR Table B item 0 14 018"
::= { essBufrRadiation 18 }

-- 5.9.6 Total Radiation
-- This object has been deprecated.
essTotalRadiation OBJECT-TYPE
  SYNTAX       Integer32 (-2048..2049)
  UNITS        "joules per square meter"
  MAX-ACCESS   read-only
  STATUS       deprecated
  DESCRIPTION
    "<Definition> The average total radiation hitting the earth's surface in watts per square meter during the radiation period. 
    <Format>
The value of 2049 shall indicate a missing value.
    <Parameter Type> status
    <Superseded by> essTotalRadiationV4
    <Informative> This object was deprecated in version 04. 
    <Object Identifier> 1.3.6.1.4.1.1206.4.2.5.1.14.25"
  REFERENCE    "WMO Code Form FM 94 BUFR Table B item 0 14 025"
::= { essBufrRadiation 25 }

-- 5.9.7 Total Radiation Period
essTotalRadiationPeriod OBJECT-TYPE
  SYNTAX       Integer32 (0..86400)
  UNITS        "seconds"
  MAX-ACCESS   read-only
  STATUS       current
  DESCRIPTION
    "<Definition> The rolling period, in seconds, that corresponds to the length of time the essTotalRadiation is averaged.
    <Parameter Type> status
    <Object Identifier> 1.3.6.1.4.1.1206.4.2.5.2.7.2"
::= { essNtcipRadiation 2 }

-- 5.9.8 Number of Radiation Sensors
radiationSensorTableNumSensors OBJECT-TYPE
  SYNTAX       Integer32 (0..255)
  UNITS        "sensors"
  MAX-ACCESS   read-only
  STATUS       current
  DESCRIPTION
    "<Definition> Indicates the number of entries in the radiation sensor table.
    <Parameter Type> status
    <Informative> This value may automatically change upon connecting or disconnecting a sensor; however, the table is still defined as a static table since the creation/deletion of rows is not managed through SNMP logic.
    <Object Identifier> 1.3.6.1.4.1.1206.4.2.5.2.7.3"
::= { essNtcipRadiation 3 }

-- 5.9.9 Radiation Sensor Table
radiationSensorTable OBJECT-TYPE
  SYNTAX       SEQUENCE OF RadiationSensorEntry
  MAX-ACCESS   not-accessible
  STATUS       current
  DESCRIPTION
    "<Definition> Table containing the radiation sensor data.
    <Object Identifier> 1.3.6.1.4.1.1206.4.2.5.2.7.4"
::= { essNtcipRadiation 4 }

-- 5.9.10 Radiation Sensor
radiationSensorEntry OBJECT-TYPE
  SYNTAX       RadiationSensorEntry
  MAX-ACCESS   not-accessible
  STATUS       current
  DESCRIPTION
    "<Definition> A radiation sensor is a sensor that reports the amount of radiation detected. It can be described through a number of attributes as indicated by the following subclauses."
  INDEX { radiationSensorIndex }
::= { radiationSensorTable 1 }

RadiationSensorEntry ::= SEQUENCE {
    radiationSensorIndex                    Integer32,
    radiationSensorHeight                   Integer32,
    radiationSensorLatitude                 Integer32,
    radiationSensorLongitude                Integer32,
    radiationSensorLocation                 SnmpAdminString,
    radiationSensorModelInformation         Integer32,
    essTotalSunV4                           Integer32,
    essInstantaneousTerrestrialRadiationV4  Integer32,
    essInstantaneousSolarRadiationV4        Integer32,
    essTotalRadiationV4                     Integer32,
    radiationSensorXOffset                  ITSInteger16,
    radiationSensorYOffset                  ITSInteger16,
    radiationSensorZOffset                  ITSInteger16,
    radiationSensorEntityID                 PhysicalIndexOrZero}

-- 5.9.10.1 Radiation Sensor Index
radiationSensorIndex OBJECT-TYPE
  SYNTAX       Integer32 (1..255)
  MAX-ACCESS   read-only
  STATUS       current
  DESCRIPTION
    "<Definition> Enumerated list of row entries that provide radiation sensor data.
    <Parameter Type> status
    <Object Identifier> 1.3.6.1.4.1.1206.4.2.5.2.7.4.1.1"
::= { radiationSensorEntry 1 }

-- 5.9.10.2 Radiation Sensor Height
-- This object has been deprecated.
radiationSensorHeight OBJECT-TYPE
  SYNTAX       Integer32 (-1000..1001)
  UNITS        "meters"
  MAX-ACCESS   read-write
  STATUS       deprecated
  DESCRIPTION
    "<Definition> The height of the radiation sensor with respect to the essReferenceHeight in meters. 
    <Format>
The value of 1001 shall indicate a missing value.
    <Parameter Type> configuration
    <Superseded by> radiationSensorZOffset
    <Informative> This object was deprecated in version 05. 
    <Object Identifier> 1.3.6.1.4.1.1206.4.2.5.2.7.4.1.2"
  REFERENCE    "essReferenceHeight plus this value equals the WMO Binary Code Form FM 94 BUFR Table B item 0 07 001."
::= { radiationSensorEntry 2 }

-- 5.9.10.3 Radiation Sensor Latitude
-- This object has been deprecated.
radiationSensorLatitude OBJECT-TYPE
  SYNTAX       Integer32 (-90000000..90000001)
  UNITS        "microdegrees latitude"
  MAX-ACCESS   read-write
  STATUS       deprecated
  DESCRIPTION
    "<Definition> The latitude in 10^-6 degrees of the ESS radiation sensor, per WGS-84 datum.
    <Format>
The radiationSensorLatitude at the North Pole is 90,000,000. The radiationSensorLatitude at the South Pole is -90,000,000. The value 90,000,001 shall indicate a missing value.
    <Parameter Type> configuration
    <Superseded by> radiationSensorYOffset
    <Informative> This object was deprecated in version 05. 
    <Object Identifier> 1.3.6.1.4.1.1206.4.2.5.2.7.4.1.3"
  REFERENCE    "Resolution based on on-going location referencing activities; the WMO Binary Code Form FM 94 BUFR Table B item 0 05 001 can be obtained by dividing this value by 10."
::= { radiationSensorEntry 3 }

-- 5.9.10.4 Radiation Sensor Longitude
-- This object has been deprecated.
radiationSensorLongitude OBJECT-TYPE
  SYNTAX       Integer32 (-180000000..180000001)
  UNITS        "microdegrees of longitude"
  MAX-ACCESS   read-write
  STATUS       deprecated
  DESCRIPTION
    "<Definition> The east longitude in 10^-6 degrees from the Prime Meridian of the ESS radiation sensor location. 
    <Format>
The radiationSensorLongitude of 180 degrees West shall be -180,000,000. The radiationSensorLongitude of 180 degrees East shall be 180,000,000. The value 180,000,001 shall indicate a missing value.
    <Parameter Type> configuration
    <Superseded by> radiationSensorXOffset
    <Informative> This object was deprecated in version 05. 
    <Object Identifier> 1.3.6.1.4.1.1206.4.2.5.2.7.4.1.4"
  REFERENCE    "Resolution based on on-going location referencing activities; the WMO Binary Code Form FM 94 BUFR Table B item 0 06 001 can be obtained by dividing this value by 10."
::= { radiationSensorEntry 4 }

-- 5.9.10.5 Radiation Sensor Location
radiationSensorLocation OBJECT-TYPE
  SYNTAX       SnmpAdminString
  MAX-ACCESS   read-write
  STATUS       current
  DESCRIPTION
    "<Definition> A textual string indicating the location of the radiation sensor.
    <Parameter Type> configuration
    <Object Identifier> 1.3.6.1.4.1.1206.4.2.5.2.7.4.1.5"
::= { radiationSensorEntry 5 }

-- 5.9.10.6 Radiation Sensor Model Information
-- This object has been deprecated.
radiationSensorModelInformation OBJECT-TYPE
  SYNTAX       Integer32 (0..255)
  MAX-ACCESS   read-write
  STATUS       deprecated
  DESCRIPTION
    "<Definition> Indicates the row in the Module Table (See NTCIP 1201) that contains information about the make, model, and version number of the sensor associated with this row of the Radiation Sensor Table.
    <Format>
The value of zero indicates that this information is not available.
    <Parameter Type> configuration
    <Supplanted by> radiationSensorEntityID
    <Informative> This object was deprecated in version 05. 
    <Object Identifier> 1.3.6.1.4.1.1206.4.2.5.2.7.4.1.6"
::= { radiationSensorEntry 6 }

-- 5.9.10.7 Total Sun V4
essTotalSunV4 OBJECT-TYPE
  SYNTAX       Integer32 (0..1441)
  UNITS        "minutes"
  MAX-ACCESS   read-only
  STATUS       current
  DESCRIPTION
    "<Definition> The total amount of sunshine in minutes over the 24 hour period preceding the observation. 
    <Format>
The value of 1441 shall indicate a missing value.
    <Parameter Type> status
    <Object Identifier> 1.3.6.1.4.1.1206.4.2.5.2.7.4.1.7"
  REFERENCE    "WMO Code Form FM 94 BUFR Table B item 0 14 031."
::= { radiationSensorEntry 7 }

-- 5.9.10.8 Terrestrial Radiation V4
essInstantaneousTerrestrialRadiationV4 OBJECT-TYPE
  SYNTAX       Integer32 (-2048..2049)
  UNITS        "watts per square meter"
  MAX-ACCESS   read-only
  STATUS       current
  DESCRIPTION
    "<Definition> The instantaneous infrared (wavelength of 3.5 - 50 micrometers) radiation being emitted from the atmosphere in watts per square meter.
    <Format>
The value of 2049 shall indicate a missing value.
    <Parameter Type> status
    <Object Identifier> 1.3.6.1.4.1.1206.4.2.5.2.7.4.1.8"
  REFERENCE    "WMO Code Form FM 94 BUFR Table B item 0 14 017"
::= { radiationSensorEntry 8 }

-- 5.9.10.9 Solar Radiation Version 4
essInstantaneousSolarRadiationV4 OBJECT-TYPE
  SYNTAX       Integer32 (-2048..2049)
  UNITS        "watts per square meter"
  MAX-ACCESS   read-only
  STATUS       current
  DESCRIPTION
    "<Definition> The instantaneous ultraviolet, visible, and near-infrared (wavelength of less than 3.0 micrometers) radiation hitting the earth's surface in watts per square meter. 
    <Format>
The value of 2049 shall indicate a missing value.
    <Parameter Type> status
    <Object Identifier> 1.3.6.1.4.1.1206.4.2.5.2.7.4.1.9"
  REFERENCE    "WMO Code Form FM 94 BUFR Table B item 0 14 018"
::= { radiationSensorEntry 9 }

-- 5.9.10.10 Total Radiation V4
essTotalRadiationV4 OBJECT-TYPE
  SYNTAX       Integer32 (-2048..2049)
  UNITS        "watts per square meter"
  MAX-ACCESS   read-only
  STATUS       current
  DESCRIPTION
    "<Definition> The average total radiation hitting the earth's surface in watts per square meter during the radiation period. 
    <Format>
The value of 2049 shall indicate a missing value.
    <Parameter Type> status
    <Object Identifier> 1.3.6.1.4.1.1206.4.2.5.2.7.4.1.10"
  REFERENCE    "WMO Code Form FM 94 BUFR Table B item 0 14 025"
::= { radiationSensorEntry 10 }

-- 5.9.10.11 Radiation Sensor X Offset
radiationSensorXOffset OBJECT-TYPE
  SYNTAX       ITSInteger16
  UNITS        "centimeters"
  MAX-ACCESS   read-write
  STATUS       current
  DESCRIPTION
    "<Definition> The offset latitude of the radiation sensor from the field device's reference location as defined by fdConfiguredLatitude and fdConfiguredLongitude. 
    <Format>
For stationary devices, the X offset shall indicate the eastward (positive) or westward (negative) distance from the reference location. For transportable and mobile devices, the X offset shall indicate distances to the starboard side (positive) or port side (negative) of the reference location on the vehicle.
    <Parameter Type> configuration
    <Object Identifier> 1.3.6.1.4.1.1206.4.2.5.2.7.4.1.11"
::= { radiationSensorEntry 11 }

-- 5.9.10.12 Radiation Sensor Y Offset
radiationSensorYOffset OBJECT-TYPE
  SYNTAX       ITSInteger16
  UNITS        "centimeters"
  MAX-ACCESS   read-write
  STATUS       current
  DESCRIPTION
    "<Definition> The Y offset of the radiation sensor from the field device's reference location as defined by fdConfiguredLatitude and fdConfiguredLongitude. 
    <Format>
For stationary devices, the Y offset shall indicate the northward (positive) or southward (negative) distance from the reference location. For transportable and mobile devices, the Y offset shall indicate distances to the fore (positive) or aft (negative) of the reference location on the vehicle.
    <Parameter Type> configuration
    <Object Identifier> 1.3.6.1.4.1.1206.4.2.5.2.7.4.1.12"
::= { radiationSensorEntry 12 }

-- 5.9.10.13 Radiation Sensor Z Offset
radiationSensorZOffset OBJECT-TYPE
  SYNTAX       ITSInteger16
  UNITS        "centimeters"
  MAX-ACCESS   read-write
  STATUS       current
  DESCRIPTION
    "<Definition> The offset elevation of the radiation sensor from the fdConfiguredElevation in centimeters.
    <Format>
Upward offsets shall be positive and downward offsets shall be negative. 
    <Parameter Type> configuration
    <Object Identifier> 1.3.6.1.4.1.1206.4.2.5.2.7.4.1.13"
::= { radiationSensorEntry 13 }

-- 5.9.10.14 Radiation Sensor Entity Identifier
radiationSensorEntityID OBJECT-TYPE
  SYNTAX       PhysicalIndexOrZero
  MAX-ACCESS   read-only
  STATUS       current
  DESCRIPTION
    "<Definition> Indicates the row in the entPhysicalTable (See RFC 4133) that contains information about the sensor, such as the manufacturer, model, and hardware and software revision identifiers. 
    <Format>
The value of zero indicates that this information is not available.
    <Parameter Type> status
    <Informative> The mechanism used to configure this value when adding or modifying a sensor is not defined by this document and is considered manufacturer-specific.
    <Object Identifier> 1.3.6.1.4.1.1206.4.2.5.2.7.4.1.14"
::= { radiationSensorEntry 14 }

-- 5.9.11 Cloud Cover Situation V4
essCloudSituationV4 OBJECT-TYPE
  SYNTAX       Integer32 (0..8)
  MAX-ACCESS   read-only
  STATUS       current
  DESCRIPTION
    "<Definition> Describes the amount of cloud cover in the sky, measured in oktas, as defined in WMO code table 2700.
    <Format>
Defined values are: 
Oktas  Category    Definition
0     Fine      Sky clear 
1  Fine      1/8 of sky covered or less, but not zero
2  Fine      2/8 of sky covered
3     Partly Cloudy  3/8 of sky covered 
4     Partly Cloudy  4/8 of sky covered
5     Partly Cloudy  5/8 of sky covered
6     Cloudy    6/8 of sky covered 
7     Cloudy    7/8 of sky covered or more, but not 8/8
8     Overcast    8/8 of sky completely covered, no breaks 
    <Parameter Type> status
    <Object Identifier> 1.3.6.1.4.1.1206.4.2.5.2.7.5"
::= { essNtcipRadiation 5 }

-- 5.10 Visibility Data Objects
essNtcipVisibility OBJECT-IDENTITY
    STATUS       current
  DESCRIPTION
    "<Definition> Objects used to describe the visibility data that is collected by the ESS.
    <Object Identifier> 1.3.6.1.4.1.1206.4.2.5.2.8"
::= {essNtcip 8 }

-- 5.10.1 Visibility
-- This object has been deprecated.
essVisibility OBJECT-TYPE
  SYNTAX       Integer32 (0..1000001)
  UNITS        "decimeters"
  MAX-ACCESS   read-only
  STATUS       deprecated
  DESCRIPTION
    "<Definition> Surface visibility measured in one tenth of a meter. 
    <Format>
The value 1000001 shall indicate an error condition or missing value.
    <Parameter Type> status
    <Superseded by> essVisibilitySensorCurrentReading
    <Informative> This object was deprecated in version 04. 
    <Object Identifier> 1.3.6.1.4.1.1206.4.2.5.2.8.1"
  REFERENCE    "The value for WMO Code Form FM 94 BUFR Table B item 0 20 001 is given by this value divided by 100."
::= { essNtcipVisibility 1 }

-- 5.10.2 Number of Visibility Sensors
essNumVisibilitySensors OBJECT-TYPE
  SYNTAX       Integer32 (0..255)
  UNITS        "sensors"
  MAX-ACCESS   read-only
  STATUS       current
  DESCRIPTION
    "<Definition> Indicates the number of entries in the visibility sensor table.
    <Parameter Type> status
    <Informative> This value may automatically change upon connecting or disconnecting a sensor; however, the table is still defined as a static table since the creation/deletion of rows is not managed through SNMP logic.
    <Object Identifier> 1.3.6.1.4.1.1206.4.2.5.2.8.2"
::= { essNtcipVisibility 2 }

-- 5.10.3 Visibility Situation
essVisibilitySituation OBJECT-TYPE
  SYNTAX       INTEGER {
    other (1),
    unknown (2),
    clear (3),
    fogNotPatchy (4),
    patchyFog (5),
    blowingSnow (6),
    smoke (7),
    seaSpray (8),
    vehicleSpray (9),
    blowingDustOrSand (10),
    sunGlare (11),
    swarmsOfInsects (12) }
  MAX-ACCESS   read-only
  STATUS       current
  DESCRIPTION
    "<Definition> Describes the travel environment in terms of visibility. If one exists, the corresponding BUFR value is indicated for staffed (BUFRs) and automated (BUFRa) stations. The indicated value can be found in the BUFR Table referenced below.
    <Format>
Range    BUFRs    BUFRa    Meaning
  1            other visibility anomaly
  2            unknown
  3    0    100    clear
  4    44    130    Fog - not patchy
  5    41    131    Patchy fog
  6    36    127    Blowing snow
  7    04    104    Smoke
  8    07    207    Sea Spray
  9            Vehicle Spray
  10    31    127    Blowing dust or sand
  11            sun glare
  12            Swarms of insects
    <Parameter Type> status
    <Object Identifier> 1.3.6.1.4.1.1206.4.2.5.2.8.3"
  REFERENCE    "The values identified in the above table for BUFRa and BUFRs can be found in WMO Code Form FM 94 BUFR Table B item 0 20 003."
::= { essNtcipVisibility 3 }

-- 5.10.4 Visibility Sensor Height
-- This object has been deprecated.
visibilitySensorHeight OBJECT-TYPE
  SYNTAX       Integer32 (-1000..1001)
  UNITS        "meters"
  MAX-ACCESS   read-write
  STATUS       deprecated
  DESCRIPTION
    "<Definition> The height of the visibility sensor with respect to the essReferenceHeight in meters. 
    <Format>
The value of 1001 shall indicate a missing value.
    <Parameter Type> configuration
    <Superseded by> essVisibilitySensorZOffset
    <Informative> This object was deprecated in version 05. 
    <Object Identifier> 1.3.6.1.4.1.1206.4.2.5.2.8.4"
  REFERENCE    "essReferenceHeight plus this value equals the WMO Binary Code Form FM 94 BUFR Table B item 0 07 001."
::= { essNtcipVisibility 4 }

-- 5.10.5 Visibility Sensor Latitude
-- This object has been deprecated.
visibilitySensorLatitude OBJECT-TYPE
  SYNTAX       Integer32 (-90000000..90000001)
  UNITS        "microdegrees latitude"
  MAX-ACCESS   read-write
  STATUS       deprecated
  DESCRIPTION
    "<Definition> The latitude in 10^-6 degrees of the ESS visibility sensor, per WGS-84 datum.
    <Format>
The visibilitySensorLatitude at the North Pole is 90,000,000. The visibilitySensorLatitude at the South Pole is -90,000,000. The value 90,000,001 shall indicate a missing value.
    <Parameter Type> configuration
    <Superseded by> essVisibilitySensorYOffset
    <Informative> This object was deprecated in version 05. 
    <Object Identifier> 1.3.6.1.4.1.1206.4.2.5.2.8.5"
  REFERENCE    "Resolution based on on-going location referencing activities; the WMO Binary Code Form FM 94 BUFR Table B item 0 05 001 can be obtained by dividing this value by 10."
::= { essNtcipVisibility 5 }

-- 5.10.6 Visibility Sensor Longitude
-- This object has been deprecated.
visibilitySensorLongitude OBJECT-TYPE
  SYNTAX       Integer32 (-180000000..180000001)
  UNITS        "microdegrees longitude"
  MAX-ACCESS   read-write
  STATUS       deprecated
  DESCRIPTION
    "<Definition> The east longitude in 10^-6 degrees from the Prime Meridian of the ESS visibility sensor location.
    <Format>
The visibilitySensorLongitude of 180 degrees West shall be -180,000,000. The visibilitySensorLongitude of 180 degrees East shall be 180,000,000. The value 180,000,001 shall indicate a missing value.
    <Parameter Type> configuration
    <Superseded by> essVisibilitySensorXOffset
    <Informative> This object was deprecated in version 05. 
    <Object Identifier> 1.3.6.1.4.1.1206.4.2.5.2.8.6"
  REFERENCE    "Resolution based on on-going location referencing activities; the WMO Binary Code Form FM 94 BUFR Table B item 0 06 001 can be obtained by dividing this value by 10."
::= { essNtcipVisibility 6 }

-- 5.10.7 Visibility Sensor Location
-- This object has been deprecated.
visibilitySensorLocation OBJECT-TYPE
  SYNTAX       DisplayString (SIZE (0..255))
  MAX-ACCESS   read-write
  STATUS       deprecated
  DESCRIPTION
    "<Definition> A textual string indicating the location of the visibility sensor.
    <Parameter Type> configuration
    <Superseded by> essVisibilitySensorLocation
    <Informative> This object was deprecated in version 05. 
    <Object Identifier> 1.3.6.1.4.1.1206.4.2.5.2.8.7"
::= { essNtcipVisibility 7 }

-- 5.10.8 Visibility Sensor Model Information
-- This object has been deprecated.
visibilitySensorModelInformation OBJECT-TYPE
  SYNTAX       Integer32 (0..255)
  MAX-ACCESS   read-write
  STATUS       deprecated
  DESCRIPTION
    "<Definition> Indicates the row in the Module Table (See NTCIP 1201) that contains information about the make, model, and version number of the visibility sensor. If there is more than one visibility sensor, the row indicates the information for the primary visibility sensor.
    <Format>
The value of zero indicates that this information is not available.
    <Parameter Type> configuration
    <Superseded by> essVisibilitySensorEntityID
    <Informative> This object was deprecated in version 05. 
    <Object Identifier> 1.3.6.1.4.1.1206.4.2.5.2.8.8"
::= { essNtcipVisibility 8 }

-- 5.10.9 Visibility Sensor Table
essVisibilitySensorTable OBJECT-TYPE
  SYNTAX       SEQUENCE OF EssVisibilitySensorEntry
  MAX-ACCESS   not-accessible
  STATUS       current
  DESCRIPTION
    "<Definition> Table containing the visibility sensor data.
    <Object Identifier> 1.3.6.1.4.1.1206.4.2.5.2.8.9"
::= { essNtcipVisibility 9 }

-- 5.10.10 Visibility Sensor
essVisibilitySensorEntry OBJECT-TYPE
  SYNTAX       EssVisibilitySensorEntry
  MAX-ACCESS   not-accessible
  STATUS       current
  DESCRIPTION
    "<Definition> A visibility sensor is a sensor that reports the surface visibility distance. It can be described through a number of attributes as indicated by the following subclauses.
    <Object Identifier> 1.3.6.1.4.1.1206.4.2.5.2.8.9.1"
  INDEX { essPressureSensorIndex }
::= { essVisibilitySensorTable 1 }

EssVisibilitySensorEntry ::= SEQUENCE {
  essVisibilitySensorIndex                Integer32,
  essVisibilitySensorLocation             SnmpAdminString,
  essVisibilitySensorXOffset              ITSInteger16,
  essVisibilitySensorYOffset              ITSInteger16,
  essVisibilitySensorZOffset              ITSInteger16,
  essVisibilitySensorDirection            Integer32,
  essVisibilitySensorEntityID             PhysicalIndexOrZero,
  essVisibilitySensorCurrentReading       Integer32 }

-- 5.10.10.1 Visibility Sensor Index
essVisibilitySensorIndex OBJECT-TYPE
  SYNTAX       Integer32 (1..255)
  MAX-ACCESS   not-accessible
  STATUS       current
  DESCRIPTION
    "<Definition> Enumerated list of row entries that provide visibility sensor data.
    <Object Identifier> 1.3.6.1.4.1.1206.4.2.5.2.8.9.1.1"
::= { essVisibilitySensorEntry 1 }

-- 5.10.10.2 Visibility Sensor Location
essVisibilitySensorLocation OBJECT-TYPE
  SYNTAX       SnmpAdminString
  MAX-ACCESS   read-write
  STATUS       current
  DESCRIPTION
    "<Definition> A textual string indicating the location of the visibility sensor.
    <Parameter Type> configuration
    <Informative> Implementations are only required to support the NVT-ASCII character set but may support additional UTF-8 characters.
    <Object Identifier> 1.3.6.1.4.1.1206.4.2.5.2.8.9.1.2"
::= { essVisibilitySensorEntry 2 }

-- 5.10.10.3 Visibility Sensor X Offset
essVisibilitySensorXOffset OBJECT-TYPE
  SYNTAX       ITSInteger16
  UNITS        "centimeters"
  MAX-ACCESS   read-write
  STATUS       current
  DESCRIPTION
    "<Definition> The lateral offset of the visibility sensor from the field device's reference location as defined by fdConfiguredLatitude and fdConfiguredLongitude. 
    <Format>
For stationary devices, the X offset shall indicate the eastward (positive) or westward (negative) distance from the reference location. For transportable and mobile devices, the X offset shall indicate distances to the starboard side (positive) or port side (negative) of the reference location on the vehicle.
    <Parameter Type> configuration
    <Object Identifier> 1.3.6.1.4.1.1206.4.2.5.2.8.9.1.3"
::= { essVisibilitySensorEntry 3 }

-- 5.10.10.4 Visibility Sensor Y Offset
essVisibilitySensorYOffset OBJECT-TYPE
  SYNTAX       ITSInteger16
  UNITS        "centimeters"
  MAX-ACCESS   read-write
  STATUS       current
  DESCRIPTION
    "<Definition> The Y offset of the visibility sensor from the field device's reference location as defined by fdConfiguredLatitude and fdConfiguredLongitude. 
    <Format>
For stationary devices, the Y offset shall indicate the northward (positive) or southward (negative) distance from the reference location. For transportable and mobile devices, the Y offset shall indicate distances to the fore (positive) or aft (negative) of the reference location on the vehicle.
    <Parameter Type> configuration
    <Object Identifier> 1.3.6.1.4.1.1206.4.2.5.2.8.9.1.4"
::= { essVisibilitySensorEntry 4 }

-- 5.10.10.5 Visibility Sensor Z Offset
essVisibilitySensorZOffset OBJECT-TYPE
  SYNTAX       ITSInteger16
  UNITS        "centimeters"
  MAX-ACCESS   read-write
  STATUS       current
  DESCRIPTION
    "<Definition> The offset elevation of the visibility sensor from the fdConfiguredElevation in centimeters.
    <Format>
Upward offsets shall be positive and downward offsets shall be negative. 
    <Parameter Type> configuration
    <Object Identifier> 1.3.6.1.4.1.1206.4.2.5.2.8.9.1.5"
::= { essVisibilitySensorEntry 5 }

-- 5.10.10.6 Visibility Sensor Direction
essVisibilitySensorDirection OBJECT-TYPE
  SYNTAX       Integer32 (-3..359)
  UNITS        "compass degrees"
  MAX-ACCESS   read-only
  STATUS       current
  DESCRIPTION
    "<Definition> The direction in which the sensor measures visibility.
    <Format>
Values 0..359 indicate degrees from true north (e.g., 90 indicates east) for sensors that detect back scatter from a distance (e.g., LIDAR). The value -1 indicates an error condition. The value -2 shall indicate a missing or unknown value. The value -3 shall indicate that the sensor detects a localized extinction coefficient to calculate visibility range (e.g., forward scatter and transmissometer sensors).  This format is consist with ITSDirection with the addition of the -3 value.
    <Parameter Type> status
    <Informative> The mechanism used to configure this value when adding or modifying a sensor is not defined by this document and is considered manufacturer-specific.
    <Object Identifier> 1.3.6.1.4.1.1206.4.2.5.2.8.9.1.6"
::= { essVisibilitySensorEntry 6 }

-- 5.10.10.7 Visibility Sensor Entity Identifier
essVisibilitySensorEntityID OBJECT-TYPE
  SYNTAX       PhysicalIndexOrZero
  MAX-ACCESS   read-only
  STATUS       current
  DESCRIPTION
    "<Definition> Indicates the row in the entPhysicalTable (See RFC 4133) that contains information about the sensor, such as the manufacturer, model, and hardware and software revision identifiers. 
    <Format>
The value of zero indicates that this information is not available.
    <Parameter Type> status
    <Informative> The mechanism used to configure this value when adding or modifying a sensor is not defined by this document and is considered manufacturer-specific.
    <Object Identifier> 1.3.6.1.4.1.1206.4.2.5.2.8.9.1.7"
::= { essVisibilitySensorEntry 7 }

-- 5.10.10.8 Visibility Sensor Current Reading
essVisibilitySensorCurrentReading OBJECT-TYPE
  SYNTAX       Integer32 (0..65535)
  UNITS        "decimeters (1/10ths of meter)"
  MAX-ACCESS   read-only
  STATUS       current
  DESCRIPTION
    "<Definition> Indicates the current surface visibility reading.
    <Format>
A value of 65535 shall indicate an error condition or missing value.
    <Parameter Type> status
    <Object Identifier> 1.3.6.1.4.1.1206.4.2.5.2.16.2.1.8"
  REFERENCE    "WMO Binary Code Form FM 94 BUFR Table B item 0 07 004."
::= { essVisibilitySensorEntry 8 }

-- 5.11 Pavement Sensor Objects
essNtcipPavement OBJECT-IDENTITY
    STATUS       current
  DESCRIPTION
    "<Definition> Objects used to describe the data that is collected by the pavement surface sensor. 
    <Object Identifier> 1.3.6.1.4.1.1206.4.2.5.2.9"
::= {essNtcip 9}

-- 5.11.1 Number of Pavement Sensors
numEssPavementSensors OBJECT-TYPE
  SYNTAX       Integer32 (0..255)
  UNITS        "sensors"
  MAX-ACCESS   read-only
  STATUS       current
  DESCRIPTION
    "<Definition> Indicates the number of entries in the pavement sensor table.
    <Parameter Type> status
    <Informative> This value may automatically change upon connecting or disconnecting a sensor; however, the table is still defined as a static table since the creation/deletion of rows is not managed through SNMP logic.
    <Object Identifier> 1.3.6.1.4.1.1206.4.2.5.2.9.1"
::= { essNtcipPavement 1 }

-- 5.11.2 Pavement Sensor Table
essPavementSensorTable OBJECT-TYPE
  SYNTAX       SEQUENCE OF EssPavementSensorEntry
  MAX-ACCESS   not-accessible
  STATUS       current
  DESCRIPTION
    "<Definition> Table containing the pavement sensor data.
    <Object Identifier> 1.3.6.1.4.1.1206.4.2.5.2.9.2"
::= { essNtcipPavement 2 }

-- 5.11.3 Pavement Sensor
essPavementSensorEntry OBJECT-TYPE
  SYNTAX       EssPavementSensorEntry
  MAX-ACCESS   not-accessible
  STATUS       current
  DESCRIPTION
    "<Definition> A pavement sensor is a sensor that reports the temperature and moisture condition of the roadway pavement. It can be described through a number of attributes as indicated by the following subclauses."
  INDEX { essPavementSensorIndex }
::= { essPavementSensorTable 1 }

EssPavementSensorEntry ::= SEQUENCE {
    essPavementSensorIndex            Integer32,
    essPavementSensorLocation         SnmpAdminString,
    essPavementType                   INTEGER,
    essPavementElevation              Integer32,
    essPavementExposure               Integer32,
    essPavementSensorType             INTEGER,
    essSurfaceStatus                  INTEGER,
    essSurfaceTemperature             Integer32,
    essPavementTemperature            Integer32,
    essSurfaceWaterDepth              Integer32,
    essSurfaceSalinity                Integer32,
    essSurfaceConductivity            Integer32,
    essSurfaceFreezePoint             Integer32,
    essSurfaceBlackIceSignal          INTEGER,
    essPavementSensorError            INTEGER,
    essSurfaceIceOrWaterDepth         Integer32,
    essSurfaceConductivityV2          Integer32,
    pavementSensorModelInformation    Integer32,
    pavementSensorTemperatureDepth    Integer32,
    pavementSensorLatitude            Integer32,
    pavementSensorLongitude           Integer32,
    pavementSensorSurfaceCondition    INTEGER,
    pavementSensorForecastCondition   INTEGER,
    pavementSensorFrictionCoefficient Integer32,
    pavementMonitorLatitude           Integer32,
    pavementMonitorLongitude          Integer32,
    pavementIcePercentage             Integer32,
    essPavementMonitorXOffset         ITSInteger16,
    essPavementMonitorYOffset         ITSInteger16,
    essPavementMonitorZOffset         ITSInteger16,
    essPavementMonitorArea            Unsigned32,
    essPavementSensorXOffset          ITSInteger16,
    essPavementSensorYOffset          ITSInteger16,
    essPavementSensorEntityID         PhysicalIndexOrZero }

-- 5.11.3.1 Pavement Sensor Index
essPavementSensorIndex OBJECT-TYPE
  SYNTAX       Integer32 (1..255)
  MAX-ACCESS   read-only
  STATUS       current
  DESCRIPTION
    "<Definition> Enumerated list of row entries that provide surface sensor data.
    <Parameter Type> status
    <Object Identifier> 1.3.6.1.4.1.1206.4.2.5.2.9.2.1.1"
::= { essPavementSensorEntry 1 }

-- 5.11.3.2 Pavement Sensor Location
essPavementSensorLocation OBJECT-TYPE
  SYNTAX       SnmpAdminString
  MAX-ACCESS   read-write
  STATUS       current
  DESCRIPTION
    "<Definition> A textual string indicating the location of the pavement sensor and the location of the pavement being monitored.
    <Parameter Type> configuration
    <Object Identifier> 1.3.6.1.4.1.1206.4.2.5.2.9.2.1.2"
::= { essPavementSensorEntry 2 }

-- 5.11.3.3 Pavement Type
essPavementType OBJECT-TYPE
  SYNTAX       INTEGER {
    other (1),
    unknown (2),
    asphalt (3),
    openGradedAsphalt (4),
    concrete (5),
    steelBridge (6),
    concreteBridge (7),
    asphaltOverlayBridge (8),
    timberBridge (9)}
  MAX-ACCESS   read-write
  STATUS       current
  DESCRIPTION
    "<Definition> Indicates the type of pavement on the roadway.
    <Format>
other                 a different type of bridge deck 
unknown               the data was never recorded in the system or is a 
                      mobile sensor
asphalt               asphalt pavement on ground 
concrete              concrete pavement on ground 
steelBridgeconcrete   a concrete driving surface on a steel girder bridge 
steelBridgeAsphalt    an asphalt driving surface on a steel girder bridge 
steelBridge           a steel lattice driving surface on the bridge 
concreteBridge        a concrete driving surface on a concrete bridge 
concreteBridgeAsphalt an asphalt overlay driving surface on a concrete 
                      bridge 
timberBridge          a wooden deck driving surface on the bridge
    <Parameter Type> configuration
    <Object Identifier> 1.3.6.1.4.1.1206.4.2.5.2.9.2.1.3"
::= { essPavementSensorEntry 3 }

-- 5.11.3.4 Pavement Elevation
-- This object has been deprecated.
essPavementElevation OBJECT-TYPE
  SYNTAX       Integer32 (-1000..1001)
  UNITS        "meters"
  MAX-ACCESS   read-write
  STATUS       deprecated
  DESCRIPTION
    "<Definition> The elevation of the street surface in meters with respect to the essReferenceHeight. 
    <Format>
The value 1001 shall indicate a missing value.
    <Parameter Type> configuration
    <Superseded by> essPavementZOffset
    <Informative> This object was deprecated in version 05. 
    <Object Identifier> 1.3.6.1.4.1.1206.4.2.5.2.9.2.1.4"
::= { essPavementSensorEntry 4 }

-- 5.11.3.5 Pavement Exposure
essPavementExposure OBJECT-TYPE
  SYNTAX       Integer32 (0..101)
  UNITS        "percent exposure"
  MAX-ACCESS   read-write
  STATUS       current
  DESCRIPTION
    "<Definition> Indicates a very rough percentage of the solar energy which is anticipated to directly hit the sensor. 
    <Format>
A value of 100 indicates a fully visible sky. A value of 101 shall indicate a missing value.
    <Parameter Type> configuration
    <Object Identifier> 1.3.6.1.4.1.1206.4.2.5.2.9.2.1.5"
::= { essPavementSensorEntry 5 }

-- 5.11.3.6 Pavement Sensor Type
essPavementSensorType OBJECT-TYPE
  SYNTAX       INTEGER {
    other (1),
    contactPassive (2),
    contactActive (3),
    infrared (4),
    radar (5),
    vibrating (6),
    microwave (7),
    laser (8),
    audio (9) }
  MAX-ACCESS   read-only
  STATUS       current
  DESCRIPTION
    "<Definition> A value indicating the type of pavement sensor.
    <Parameter Type> status
    <Informative> The value 'laser' was added in v02. The value 'audio' was added in v05.
    <Object Identifier> 1.3.6.1.4.1.1206.4.2.5.2.9.2.1.6"
::= { essPavementSensorEntry 6 }

-- 5.11.3.7 Surface Status
-- This object has been deprecated.
essSurfaceStatus OBJECT-TYPE
  SYNTAX       INTEGER {
    other (1),
    error (2),
    dry (3),
    traceMoisture (4),
    wet (5),
    chemicallyWet (6),
    iceWarning (7),
    iceWatch (8),
    snowWarning (9),
    snowWatch (10),
    absorption (11),
    dew (12),
    frost (13),
    absorptionAtDewpoint (14) }
  MAX-ACCESS   read-only
  STATUS       deprecated
  DESCRIPTION
    "<Definition> A value indicating the pavement surface status.
    <Format>
other - The value reported by the sensor is not defined by the standard. 
    See the manufacturer's documentation for more information.
noReport - The sensor is not providing any reading for surface status and 
    may not be responding
errorReport - The sensor is providing a reading for surface status, but 
    either the reading indicates an error code or the data has been deemed 
    invalid or suspect
dry - The sensor does not detect any moisture or unusual conditions.
trace - The sensor detects some moisture, but it is suspected to be 
    isolated
absorption - A salt chemical is present that is not fully dissolved in 
    water. As a result, the conductivity readings result in erroneous 
    calculations for amount of chemical in the mix. 
wet - The sensor detects a significant amount of moisture indicating a wet 
    roadway.
chemically wet - The sensor detects a signaificant amount of moisture 
    mixed with a de-icing or anti-icing chemical
dew - The sensor detects moisture that is suspected to be from the 
    formation of dew
frost - The sensor detects the formation of frost
freezeAdvisory - The risk of the formation of some sort of frozen moisture 
    on the roadway is elevated, but its occurrence, location, and/or 
    timing is still uncertain
slushAdvisory - The risk of the accumulation of snow or slush on the 
    roadway is elevated, but its occurrence, location, and/or timing is 
    still uncertain
iceAdvisory - The risk of the formation of ice or black ice on the roadway 
    is elevated, but its occurrence, location, and/or timing is still 
    uncertain
freezeHazard - The sensor detects some sort of frozen moisture but is 
    unable to classify as slush or ice.
slush - The sensor detects snow or slush.
ice - The sensor detects ice or black ice. (See essSurfaceBlackIceSignal)
    <Parameter Type> status
    <Superseded by> pavementSesnsorSurfaceCondition and pavementSensorForecastCondition
    <Informative> This object was deprecated in version 04. 
    <Object Identifier> 1.3.6.1.4.1.1206.4.2.5.2.9.2.1.7"
::= { essPavementSensorEntry 7 }

-- 5.11.3.8 Surface Temperature
essSurfaceTemperature OBJECT-TYPE
  SYNTAX       Integer32 (-1000..1001)
  UNITS        "tenths of degrees Celsius"
  MAX-ACCESS   read-only
  STATUS       current
  DESCRIPTION
    "<Definition> The current pavement surface temperature in tenths of degrees Celsius.
    <Format>
The value 1001 shall indicate an error condition or missing value.
    <Parameter Type> status
    <Object Identifier> 1.3.6.1.4.1.1206.4.2.5.2.9.2.1.8"
::= { essPavementSensorEntry 8 }

-- 5.11.3.9 Pavement Temperature
essPavementTemperature OBJECT-TYPE
  SYNTAX       Integer32 (-1000..1001)
  UNITS        "tenths of degrees Celsius"
  MAX-ACCESS   read-only
  STATUS       current
  DESCRIPTION
    "<Definition> The current pavement temperature 2-10 cm below the pavement surface in tenths of degrees Celsius. The specific depth at which the reading is taken is defined by pavementSensorTemperatureDepth.
    <Format>
The value 1001 shall indicate an error condition or missing value.
    <Parameter Type> status
    <Object Identifier> 1.3.6.1.4.1.1206.4.2.5.2.9.2.1.9"
::= { essPavementSensorEntry 9 }

-- 5.11.3.10 Surface Water Depth
-- This object has been deprecated.
essSurfaceWaterDepth OBJECT-TYPE
  SYNTAX       Integer32 (0..255)
  UNITS        "millimeters"
  MAX-ACCESS   read-only
  STATUS       deprecated
  DESCRIPTION
    "<Definition> The current depth of water on the surface of the roadway measured in millimeters. The value 255 shall indicate an error condition or missing value.
    <Parameter Type> status
    <Superseded by> essSurfaceIceOrWaterDepth
    <Informative> This object was deprecated in version 2. 
    <Object Identifier> 1.3.6.1.4.1.1206.4.2.5.2.9.2.1.10"
::= { essPavementSensorEntry 10 }

-- 5.11.3.11 Surface Salinity
essSurfaceSalinity OBJECT-TYPE
  SYNTAX       Integer32 (0..65535)
  UNITS        "parts per 100,000 by weight"
  MAX-ACCESS   read-only
  STATUS       current
  DESCRIPTION
    "<Definition> The pavement salinity in parts per one hundred thousand by weight (i.e., grams of solute per 100,000 grams of solution). 
    <Format>
The value 65535 shall indicate an error condition or missing value.
    <Parameter Type> status
    <Object Identifier> 1.3.6.1.4.1.1206.4.2.5.2.9.2.1.11"
::= { essPavementSensorEntry 11 }

-- 5.11.3.12 Surface Conductivity
-- This object has been deprecated.
essSurfaceConductivity OBJECT-TYPE
  SYNTAX       Integer32 (0..65535)
  UNITS        "mhos"
  MAX-ACCESS   read-only
  STATUS       deprecated
  DESCRIPTION
    "<Definition> Indicates the conductance of the ice/liquid mixture on the pavement as detected by the sensor, in mhos, which is the inverse of ohms. The value 65535 shall indicate an error condition or missing value.
    <Parameter Type> status
    <Superseded by> essSurfaceConductivityV2
    <Informative> This object was deprecated in version 2. 
    <Object Identifier> 1.3.6.1.4.1.1206.4.2.5.2.9.2.1.12"
::= { essPavementSensorEntry 12 }

-- 5.11.3.13 Surface Freezing Point
essSurfaceFreezePoint OBJECT-TYPE
  SYNTAX       Integer32 (-1000..1001)
  UNITS        "tenths of degrees Celsius"
  MAX-ACCESS   read-only
  STATUS       current
  DESCRIPTION
    "<Definition> The temperature in tenths of degrees Celsius at which the existing solution on the roadway freezes.
    <Format>
The value 1001 shall indicate an error condition or missing value.
    <Parameter Type> status
    <Object Identifier> 1.3.6.1.4.1.1206.4.2.5.2.9.2.1.13"
::= { essPavementSensorEntry 13 }

-- 5.11.3.14 Surface Black Ice Signal
essSurfaceBlackIceSignal OBJECT-TYPE
  SYNTAX       INTEGER {
    other (1),
    noIce (2),
    blackIce (3),
    detectorError (4) }
  MAX-ACCESS   read-only
  STATUS       current
  DESCRIPTION
    "<Definition> A value indicating if Black Ice is detected by the sensor.
    <Format>
other - The sensor is reporting a value that is not defined by the 
    standard. See the manufacturer's documentation for more information.
noIce - The sensor is not currently detecting black ice.
blackIce - The sensor is currently detecting black ice.
detectorError - The sensor is not connected, is not reporting, or is 
    reporting an error.
    <Parameter Type> status
    <Object Identifier> 1.3.6.1.4.1.1206.4.2.5.2.9.2.1.14"
::= { essPavementSensorEntry 14 }

-- 5.11.3.15 Pavement Sensor Error
essPavementSensorError OBJECT-TYPE
  SYNTAX       INTEGER {
    other (1),
    none (2),
    noResponse (3),
    cutCable (4),
    shortCircuit (5),
    dirtyLens (6) }
  MAX-ACCESS   read-only
  STATUS       current
  DESCRIPTION
    "<Definition> A value indicating the type of pavement sensor error.
    <Format>
other - An error has been detected that is not defined by the standard; 
    see the manufacturer's documentation for more information.
none - No error is detected, the sensor appears to be working properly
noResponse - The sensor is configured and is believed to be connected, 
    but is not responding
cutCable - The sensor is not configured, not present or not fully 
    connected, perhaps because the cable was cut
shortCircuit - The sensor input has detected a short-circuit.
dirtyLens - The lens of the sensor appears to be dirty.
    <Parameter Type> status
    <Object Identifier> 1.3.6.1.4.1.1206.4.2.5.2.9.2.1.15"
::= { essPavementSensorEntry 15 }

-- 5.11.3.16 Surface Water Depth—Version 2
essSurfaceIceOrWaterDepth OBJECT-TYPE
  SYNTAX       Integer32 (0..65535)
  UNITS        "tenths of millimeters"
  MAX-ACCESS   read-only
  STATUS       current
  DESCRIPTION
    "<Definition> The current thickness of ice or depth of water on the surface of the roadway measured in 1/10th of millimeters. 
    <Format>
The value 65535 shall indicate an error condition or missing value.
    <Parameter Type> status
    <Object Identifier> 1.3.6.1.4.1.1206.4.2.5.2.9.2.1.16"
::= { essPavementSensorEntry 16 }

-- 5.11.3.17 Surface Conductivity—Version 2
essSurfaceConductivityV2 OBJECT-TYPE
  SYNTAX       Integer32 (0..65535)
  UNITS        "tenths of milli-mhos/cm"
  MAX-ACCESS   read-only
  STATUS       current
  DESCRIPTION
    "<Definition> Indicates the conductivity of the ice/liquid mixture on the pavement as detected by the sensor, in 1/10ths of milli-mhos/cm (mhos is the inverse of ohms). This value is independent of the size or shape of the sensor and can be directly translated into a percent concentration of chemical (e.g. salinity) through look-up tables for a given chemical.
    <Format>
The value  65535 shall indicate an error condition or missing value.
    <Parameter Type> status
    <Object Identifier> 1.3.6.1.4.1.1206.4.2.5.2.9.2.1.17"
::= { essPavementSensorEntry 17 }

-- 5.11.3.18 Pavement Sensor Model Information
-- This object has been deprecated.
pavementSensorModelInformation OBJECT-TYPE
  SYNTAX       Integer32 (0..255)
  MAX-ACCESS   read-write
  STATUS       deprecated
  DESCRIPTION
    "<Definition> Indicates the row in the Module Table (See NTCIP 1201) that contains information about the make, model, and version number of the sensor associated with this row of the Pavement Sensor Table.
    <Format>
The value of zero indicates that this information is not available.
    <Parameter Type> configuration
    <Supplanted by> pavementSensorEntityID
    <Informative> This object was deprecated in version 5. 
    <Object Identifier> 1.3.6.1.4.1.1206.4.2.5.2.9.2.1.18"
::= { essPavementSensorEntry 18 }

-- 5.11.3.19 Pavement Temperature Depth
pavementSensorTemperatureDepth OBJECT-TYPE
  SYNTAX       Integer32 (2..11)
  UNITS        "centimeters"
  MAX-ACCESS   read-only
  STATUS       current
  DESCRIPTION
    "<Definition> The depth at which the pavement temperature is detected.
    <Format>
The value of 11 indicates that the information is not available.
    <Parameter Type> status
    <Informative> The mechanism used to configure this value when adding or modifying a sensor is not defined by this document and is considered manufacturer-specific.
    <Object Identifier> 1.3.6.1.4.1.1206.4.2.5.2.9.2.1.19"
::= { essPavementSensorEntry 19 }

-- 5.11.3.20 Pavement Sensor Latitude
-- This object has been deprecated.
pavementSensorLatitude OBJECT-TYPE
  SYNTAX       Integer32 (-90000000..90000001)
  UNITS        "microdegrees latitude"
  MAX-ACCESS   read-write
  STATUS       deprecated
  DESCRIPTION
    "<Definition> The latitude in 10^-6 degrees of the ESS pavement sensor, per WGS-84 datum.
    <Format>
The pavementSensorLatitude at the North Pole is 90,000,000. The pavementSensorLatitude at the South Pole is -90,000,000. The value 90,000,001 shall indicate a missing value.
    <Parameter Type> configuration
    <Superseded by> pavementSensorYOffset
    <Informative> This object was deprecated in version 05. 
    <Object Identifier> 1.3.6.1.4.1.1206.4.2.5.2.9.2.1.20"
  REFERENCE    "Resolution based on on-going location referencing activities; the WMO Binary Code Form FM 94 BUFR Table B item 0 05 001 can be obtained by dividing this value by 10."
::= { essPavementSensorEntry 20 }

-- 5.11.3.21 Pavement Sensor Longitude
-- This object has been deprecated.
pavementSensorLongitude OBJECT-TYPE
  SYNTAX       Integer32 (-180000000..180000001)
  UNITS        "microdegrees longitude"
  MAX-ACCESS   read-write
  STATUS       deprecated
  DESCRIPTION
    "<Definition> The east longitude in 10^-6 degrees from the Prime Meridian of the ESS pavement sensor location.
    <Format>
The pavementSensorLongitude of 180 degrees West shall be -180,000,000. The pavementSensorLongitude of 180 degrees East shall be 180,000,000. The value 180,000,001 shall indicate a missing value.
    <Parameter Type> configuration
    <Superseded by> pavementSensorXOffset
    <Informative> This object was deprecated in version 05. 
    <Object Identifier> 1.3.6.1.4.1.1206.4.2.5.2.9.2.1.21"
  REFERENCE    "Resolution based on on-going location referencing activities; the WMO Binary Code Form FM 94 BUFR Table B item 0 06 001 can be obtained by dividing this value by 10."
::= { essPavementSensorEntry 21 }

-- 5.11.3.22 Pavement Surface Condition
pavementSensorSurfaceCondition OBJECT-TYPE
  SYNTAX       INTEGER {
    other (1),
    error (2),
    dry (3),
    moist (4),
    chemicallyMoist(5),
    wet (6),
    chemicallyWet (7),
    standingWater (8),
    frost (9),
    slush (10),
    snow (11),
    ice (12),
    noReport (13)  }
  MAX-ACCESS   read-only
  STATUS       current
  DESCRIPTION
    "<Definition> A value indicating the pavement surface status.
    <Format>
other: The value reported by the sensor is not defined by the standard. 
    See the manufacturer's documentation for more information
error: The sensor is providing a reading for surface status, but either 
    the reading indicates an error code or the data has been deemed 
    invalid or suspect
dry: no humidity over the sensor (EN 15518-3)
moist: from 0.01 mm to 0.2 mm water film thickness over the sensor 
    (EN 15518-3)
chemically moist: from 0.01 mm to 0.2 mm water film thickness over the 
    sensor mixed with de-icing or anti-icing chemical
wet: from 0.2 mm water film thickness to 2.0 mm water film thickness over 
    the sensor (EN 15518-3)
chemically wet: from 0.2 mm water film thickness or greater mixed with 
    de-icing or anti-icing chemical
standing water: from 2.0 mm or greater water film thickness over the 
    sensor (EN 15518-3)
frost: formation of frost (ice crystals) is detected over the sensor
slush: snow or ice that has been reduced to a soft water mixture by rain, 
    warm temperature, and/or chemical treatment (Glossary of Meteorology)
snow: snow is detected over the sensor
ice: ice or black ice is detected (See essSurfaceBlackIceSignal)
noReport: The sensor is not providing any reading for surface status and 
    may not be responding
    <Parameter Type> status
    <Object Identifier> 1.3.6.1.4.1.1206.4.2.5.2.9.2.1.22"
::= { essPavementSensorEntry 22 }

-- 5.11.3.23 Pavement Forecasted Condition
pavementSensorForecastCondition OBJECT-TYPE
  SYNTAX       INTEGER {
    other (1),
    error (2),
    noAdvisory (3),
    iceAdvisory (4),
    slushAdvisory(5),
    freezeAdvisory (6),
    freezeHazard (7),
    noReport (8)  }
  MAX-ACCESS   read-only
  STATUS       current
  DESCRIPTION
    "<Definition> A value indicating the pavement surface status.
    <Format>
other: The value reported by the sensor is not defined by the standard. 
    See the manufacturer's documentation for more information.
error: The sensor is providing a reading for surface status, but either 
    the reading indicates an error code or the data has been deemed 
    invalid or suspect
noAdvisory: No frozen moisture is detected and the risk of frozen moisture 
    is low.
iceAdvisory: The risk of the formation of ice or black ice on the roadway 
    is elevated, but its occurrence, location, and/or timing is still 
    uncertain
slushAdvisory: The risk of the accumulation of snow or slush on the 
    roadway is elevated, but its occurrence, location, and/or timing is 
    still uncertain
freezeAdvisory: The risk of the formation of some sort of frozen moisture 
    on the roadway is elevated, but its occurrence, location, and/or 
    timing is still uncertain
freezeHazard: The sensor detects some sort of frozen moisture but is 
    unable to classify as slush or ice
noReport: The sensor is not providing any reading for surface status and 
    may not be responding
    <Parameter Type> status
    <Object Identifier> 1.3.6.1.4.1.1206.4.2.5.2.9.2.1.23"
::= { essPavementSensorEntry 23 }

-- 5.11.3.24 Pavement Surface Friction Coefficient
pavementSensorFrictionCoefficient OBJECT-TYPE
  SYNTAX       Integer32 (0..101)
  MAX-ACCESS   read-only
  STATUS       current
  DESCRIPTION
    "<Definition> A value representing the manufacturer's estimate of the friction coefficient of the roadway pavement for the specified pavement sensor. The actual coefficient of friction is dependent on many variables, including characteristics of the tire traveling on the pavement; thus it is recognized that it is impossible to provide a single mathematically precise value. However, the reported friction coefficient shall be based on an empirical model that has a strong correlation with actual measured friction coefficients using a standard test method and test apparatus, such as a decelerometer or a locked-wheel tester. The estimate is provided in hundredths (i.e., if the weight of a vehicle is 15,000 N and the estimated friction coefficient is 50, the resultant friction force offered by locked wheels on the pavement is expected to be approximately 15,000 N * 50/100 = 7,500 N). This value should not be compared across vendors or sites due to the number of site-specific factors that can impact its accuracy, but the value can be useful to gauge the relative friction of a specific site at different points in time. For example, this value could be used to activate a warning message, but the exact value that would trigger that condition would need to be discovered empirically at each site.
    <Format>
The value 101 shall indicate an error condition or missing value.
    <Parameter Type> status
    <Object Identifier> 1.3.6.1.4.1.1206.4.2.5.2.9.2.1.24"
::= { essPavementSensorEntry 24 }

-- 5.11.3.25 Pavement Monitoring Latitude
-- This object has been deprecated.
pavementMonitorLatitude OBJECT-TYPE
  SYNTAX       Integer32 (-90000000..90000001)
  UNITS        "microdegrees latitude"
  MAX-ACCESS   read-write
  STATUS       deprecated
  DESCRIPTION
    "<Definition> The latitude in 10^-6 degrees of the location that the ESS pavement sensor is monitoring, per WGS-84 datum. A value of 0 for this object and pavementMonitorLongitude indicates that the location being monitored is the same as defined in pavementSensorLatitude and pavementSensorLongitude.
    <Format>
The pavementMonitorLatitude at the North Pole is 90,000,000. The pavementMonitorLatitude at the South Pole is -90,000,000. The value 90,000,001 shall indicate a missing value.
    <Parameter Type> configuration
    <Superseded by> essPavementMonitorYOffset
    <Informative> This object was deprecated in version 05. 
    <Object Identifier> 1.3.6.1.4.1.1206.4.2.5.2.9.2.1.25"
  REFERENCE    "Resolution based on on-going location referencing activities; the WMO Binary Code Form FM 94 BUFR Table B item 0 05 001 can be obtained by dividing this value by 10."
::= { essPavementSensorEntry 25 }

-- 5.11.3.26 Pavement Monitoring Longitude
-- This object has been deprecated.
pavementMonitorLongitude OBJECT-TYPE
  SYNTAX       Integer32 (-180000000..180000001)
  UNITS        "microdegrees longitude"
  MAX-ACCESS   read-write
  STATUS       deprecated
  DESCRIPTION
    "<Definition> The east longitude in 10^-6 degrees from the Prime Meridian of the location that the ESS pavement sensor is monitoring. A value of 0 for this object and pavementMonitorLatitude indicates that the location being monitored is the same as defined in pavementSensorLatitude and pavementSensorLongitude.
    <Format>
The pavementMonitorLongitude of 180 degrees West shall be -180,000,000. The pavementMonitorLongitude of 180 degrees East shall be 180,000,000. The value 180,000,001 shall indicate a missing value.
    <Parameter Type> configuration
    <Superseded by> essPavementMonitorXOffset
    <Informative> This object was deprecated in version 05. 
    <Object Identifier> 1.3.6.1.4.1.1206.4.2.5.2.9.2.1.26"
  REFERENCE    "Resolution based on on-going location referencing activities; the WMO Binary Code Form FM 94 BUFR Table B item 0 06 001 can be obtained by dividing this value by 10."
::= { essPavementSensorEntry 26 }

-- 5.11.3.27 Pavement Ice Percentage
pavementIcePercentage OBJECT-TYPE
  SYNTAX       Integer32 (0..101)
  UNITS        "percent"
  MAX-ACCESS   read-only
  STATUS       current
  DESCRIPTION
    "<Definition> The percentage of ice on the surface by volume.
    <Format>
The value 101 shall indicate an error condition or missing value.
    <Parameter Type> status
    <Object Identifier> 1.3.6.1.4.1.1206.4.2.5.2.9.2.1.27"
::= { essPavementSensorEntry 27 }

-- 5.11.3.28 Pavement Monitor X Offset
essPavementMonitorXOffset OBJECT-TYPE
  SYNTAX       ITSInteger16
  UNITS        "centimeters"
  MAX-ACCESS   read-write
  STATUS       current
  DESCRIPTION
    "<Definition> The X offset of the pavement monitor site from the field device's reference location as defined by fdConfiguredLatitude and fdConfiguredLongitude. 
    <Format>
For stationary devices, the X offset shall indicate the eastward (positive) or westward (negative) distance from the reference location. For transportable and mobile devices, the X offset shall indicate distances to the starboard side (positive) or port side (negative) of the reference location on the vehicle.
    <Parameter Type> configuration
    <Object Identifier> 1.3.6.1.4.1.1206.4.2.5.2.9.2.1.28"
::= { essPavementSensorEntry 28 }

-- 5.11.3.29 Pavement Monitor Y Offset
essPavementMonitorYOffset OBJECT-TYPE
  SYNTAX       ITSInteger16
  UNITS        "centimeters"
  MAX-ACCESS   read-write
  STATUS       current
  DESCRIPTION
    "<Definition> The Y offset of the pavement monitor site from the field device's reference location as defined by fdConfiguredLatitude and fdConfiguredLongitude. 
    <Format>
For stationary devices, the Y offset shall indicate the northward (positive) or southward (negative) distance from the reference location. For transportable and mobile devices, the Y offset shall indicate distances to the fore (positive) or aft (negative) of the reference location on the vehicle.
    <Parameter Type> configuration
    <Object Identifier> 1.3.6.1.4.1.1206.4.2.5.2.9.2.1.29"
::= { essPavementSensorEntry 29 }

-- 5.11.3.30 Pavement Monitor Z Offset
essPavementMonitorZOffset OBJECT-TYPE
  SYNTAX       ITSInteger16
  UNITS        "centimeters"
  MAX-ACCESS   read-write
  STATUS       current
  DESCRIPTION
    "<Definition> The offset elevation of the pavement at the monitor site as measured from the fdConfiguredElevation in centimeters.
    <Format>
Upward offsets shall be positive and downward offsets shall be negative. 
    <Parameter Type> configuration
    <Object Identifier> 1.3.6.1.4.1.1206.4.2.5.2.9.2.1.30"
::= { essPavementSensorEntry 30 }

-- 5.11.3.31 Pavement Monitor Area
essPavementMonitorArea OBJECT-TYPE
  SYNTAX       Unsigned32
  UNITS        "square centimeters"
  MAX-ACCESS   read-only
  STATUS       current
  DESCRIPTION
    "<Definition> The nominal area monitored by this pavement sensor.
    <Format>
The value 4294967294 indicates an area of 4,294,967,295 cm^2 or larger and the value 4294967295 indicates an unknown value.
    <Parameter Type> status
    <Object Identifier> 1.3.6.1.4.1.1206.4.2.5.2.9.2.1.31"
::= { essPavementSensorEntry 31 }

-- 5.11.3.32 Pavement Sensor X Offset
essPavementSensorXOffset OBJECT-TYPE
  SYNTAX       ITSInteger16
  UNITS        "centimeters"
  MAX-ACCESS   read-write
  STATUS       current
  DESCRIPTION
    "<Definition> The X offset of the pavement sensor from the field device's reference location as defined by fdConfiguredLatitude and fdConfiguredLongitude. 
    <Format>
For stationary devices, the X offset shall indicate the eastward (positive) or westward (negative) distance from the reference location. For transportable and mobile devices, the X offset shall indicate distances to the starboard side (positive) or port side (negative) of the reference location on the vehicle.
    <Parameter Type> configuration
    <Object Identifier> 1.3.6.1.4.1.1206.4.2.5.2.9.2.1.32"
::= { essPavementSensorEntry 32 }

-- 5.11.3.33 Pavement Sensor Y Offset
essPavementSensorYOffset OBJECT-TYPE
  SYNTAX       ITSInteger16
  UNITS        "centimeters"
  MAX-ACCESS   read-write
  STATUS       current
  DESCRIPTION
    "<Definition> The Y offset of the pavement sensor from the field device's reference location as defined by fdConfiguredLatitude and fdConfiguredLongitude. 
    <Format>
For stationary devices, the Y offset shall indicate the northward (positive) or southward (negative) distance from the reference location. For transportable and mobile devices, the Y offset shall indicate distances to the fore (positive) or aft (negative) of the reference location on the vehicle.
    <Parameter Type> configuration
    <Object Identifier> 1.3.6.1.4.1.1206.4.2.5.2.9.2.1.33"
::= { essPavementSensorEntry 33 }

-- 5.11.3.34 Pavement Sensor Entity Identifier
essPavementSensorEntityID OBJECT-TYPE
  SYNTAX       PhysicalIndexOrZero
  MAX-ACCESS   read-only
  STATUS       current
  DESCRIPTION
    "<Definition> Indicates the row in the entPhysicalTable (See RFC 4133) that contains information about the sensor, such as the manufacturer, model, and hardware and software revision identifiers. 
    <Format>
The value of zero indicates that this information is not available.
    <Parameter Type> status
    <Informative> The mechanism used to configure this value when adding or modifying a sensor is not defined by this document and is considered manufacturer-specific.
    <Object Identifier> 1.3.6.1.4.1.1206.4.2.5.2.9.2.1.34"
::= { essPavementSensorEntry 34 }

-- 5.11.4 Number of Subsurface Sensors
numEssSubSurfaceSensors OBJECT-TYPE
  SYNTAX       Integer32 (0..255)
  UNITS        "sensors"
  MAX-ACCESS   read-only
  STATUS       current
  DESCRIPTION
    "<Definition> Indicates the number of entries in the Subsurface Sensor Table.
    <Parameter Type> status
    <Informative> This value may automatically change upon connecting or disconnecting a sensor; however, the table is still defined as a static table since the creation/deletion of rows is not managed through SNMP logic.
    <Object Identifier> 1.3.6.1.4.1.1206.4.2.5.2.9.3"
::= { essNtcipPavement 3 }

-- 5.11.5 Subsurface Sensor Table
essSubSurfaceSensorTable OBJECT-TYPE
  SYNTAX       SEQUENCE OF EssSubSurfaceSensorEntry
  MAX-ACCESS   not-accessible
  STATUS       current
  DESCRIPTION
    "<Definition> Table containing the subsurface sensor data.
    <Object Identifier> 1.3.6.1.4.1.1206.4.2.5.2.9.4"
::= { essNtcipPavement 4 }

-- 5.11.6 Subsurface Sensor
essSubSurfaceSensorEntry OBJECT-TYPE
  SYNTAX       EssSubSurfaceSensorEntry
  MAX-ACCESS   not-accessible
  STATUS       current
  DESCRIPTION
    "<Definition> A subsurface sensor is a sensor that reports the temperature and moisture condition of the roadway subsurface. It can be described through a number of attributes as indicated by the following subclauses."
  INDEX { essSubSurfaceSensorIndex }
::= { essSubSurfaceSensorTable 1 }

EssSubSurfaceSensorEntry ::= SEQUENCE {
    essSubSurfaceSensorIndex            Integer32,
    essSubSurfaceSensorLocation         SnmpAdminString,
    essSubSurfaceType                   INTEGER,
    essSubSurfaceSensorDepth            Integer32,
    essSubSurfaceTemperature            Integer32,
    essSubSurfaceSensorEntityID         PhysicalIndexOrZero,
    essSubSurfaceMoisture               Integer32,
    essSubSurfaceSensorError            INTEGER,
    essSubSurfaceSensorLatitude         Integer32,
    essSubSurfaceSensorLongitude        Integer32,
    essSubSurfaceSensorModelInformation Integer32,
    essSubSurfaceSensorXOffset          ITSInteger16,
    essSubSurfaceSensorYOffset          ITSInteger16 }

-- 5.11.6.1 Subsurface Sensor Index
essSubSurfaceSensorIndex OBJECT-TYPE
  SYNTAX       Integer32 (1..255)
  MAX-ACCESS   read-only
  STATUS       current
  DESCRIPTION
    "<Definition> Enumerated list of row entries that provide subsurface sensor data.
    <Parameter Type> status
    <Object Identifier> 1.3.6.1.4.1.1206.4.2.5.2.9.4.1.1"
::= { essSubSurfaceSensorEntry 1 }

-- 5.11.6.2 Subsurface Sensor Location
essSubSurfaceSensorLocation OBJECT-TYPE
  SYNTAX       SnmpAdminString
  MAX-ACCESS   read-write
  STATUS       current
  DESCRIPTION
    "<Definition> A textual string indicating the location of the subsurface sensor.
    <Parameter Type> configuration
    <Object Identifier> 1.3.6.1.4.1.1206.4.2.5.2.9.4.1.2"
::= { essSubSurfaceSensorEntry 2 }

-- 5.11.6.3 Subsurface Type
essSubSurfaceType OBJECT-TYPE
  SYNTAX       INTEGER {
    other (1),
    unknown (2),
    concrete (3),
    asphalt (4),
    openGradedAsphalt (5),
    gravel (6),
    clay (7),
    loam (8),
    sand (9),
    permafrost (10),
    variousAggregates (11),
    air (12) }
  MAX-ACCESS   read-write
  STATUS       current
  DESCRIPTION
    "<Definition> Indicates the type of subsurface. A value of air would indicate a bridge.
    <Parameter Type> configuration
    <Object Identifier> 1.3.6.1.4.1.1206.4.2.5.2.9.4.1.3"
::= { essSubSurfaceSensorEntry 3 }

-- 5.11.6.4 Subsurface Sensor Depth
essSubSurfaceSensorDepth OBJECT-TYPE
  SYNTAX       Integer32 (0..1001)
  UNITS        "centimeters"
  MAX-ACCESS   read-write
  STATUS       current
  DESCRIPTION
    "<Definition> Depth of subsurface sensor in centimeters below the pavement surface.
    <Format>
The value 1001 shall indicate an error condition or missing value.
    <Parameter Type> configuration
    <Object Identifier> 1.3.6.1.4.1.1206.4.2.5.2.9.4.1.4"
::= { essSubSurfaceSensorEntry 4 }

-- 5.11.6.5 Subsurface Temperature
essSubSurfaceTemperature OBJECT-TYPE
  SYNTAX       Integer32 (-1000..1001)
  UNITS        "tenths of degrees Celsius"
  MAX-ACCESS   read-only
  STATUS       current
  DESCRIPTION
    "<Definition> The current subsurface temperature in tenths of degrees Celsius.
    <Format>
The value 1001 shall indicate an error condition or missing value.
    <Parameter Type> status
    <Object Identifier> 1.3.6.1.4.1.1206.4.2.5.2.9.4.1.5"
::= { essSubSurfaceSensorEntry 5 }

-- 5.11.6.6 Subsurface Sensor Entity Identifier
essSubSurfaceSensorEntityID OBJECT-TYPE
  SYNTAX       PhysicalIndexOrZero
  MAX-ACCESS   read-only
  STATUS       current
  DESCRIPTION
    "<Definition> Indicates the row in the entPhysicalTable (See RFC 4133) that contains information about the sensor, such as the manufacturer, model, and hardware and software revision identifiers. 
    <Format>
The value of zero indicates that this information is not available.
    <Parameter Type> status
    <Informative> The mechanism used to configure this value when adding or modifying a sensor is not defined by this document and is considered manufacturer-specific.
    <Object Identifier> 1.3.6.1.4.1.1206.4.2.5.2.9.4.1.6"
::= { essSubSurfaceSensorEntry 6 }

-- 5.11.6.7 Subsurface Moisture
essSubSurfaceMoisture OBJECT-TYPE
  SYNTAX       Integer32 (0..101)
  UNITS        "percent moisture"
  MAX-ACCESS   read-only
  STATUS       current
  DESCRIPTION
    "<Definition> The subsurface moisture expressed as a percentage (e.g. 0 indicates dry, 100 indicates saturated).
    <Format>
The value 101 indicates an error condition or missing value.
    <Parameter Type> status
    <Object Identifier> 1.3.6.1.4.1.1206.4.2.5.2.9.4.1.7"
::= { essSubSurfaceSensorEntry 7 }

-- 5.11.6.8 Subsurface Sensor Error
essSubSurfaceSensorError OBJECT-TYPE
  SYNTAX       INTEGER {
    other (1),
    none (2),
    noResponse (3),
    cutCable (4),
    shortCircuit (5) }
  MAX-ACCESS   read-only
  STATUS       current
  DESCRIPTION
    "<Definition> A value indicating the type of sensor error.
    <Format>
other - An error has been detected that is not defined by the standard; 
    see the manufacturer's documentation for more information.
none - No error is detected, the sensor appears to be working properly
noResponse - The sensor is configured and is believed to be connected, but 
    is not responding
cutCable - The sensor is not configured, not present or not fully 
    connected, perhaps because the cable was cut
shortCircuit - The sensor input has detected a short-circuit.
    <Parameter Type> status
    <Object Identifier> 1.3.6.1.4.1.1206.4.2.5.2.9.4.1.8"
::= { essSubSurfaceSensorEntry 8 }

-- 5.11.6.9 Subsurface Sensor Latitude
-- This object has been deprecated.
essSubSurfaceSensorLatitude OBJECT-TYPE
  SYNTAX       Integer32 (-90000000..90000001)
  UNITS        "microdegrees latitude"
  MAX-ACCESS   read-write
  STATUS       deprecated
  DESCRIPTION
    "<Definition> The latitude in 10^-6 degrees of the ESS subsurface sensor, per WGS-84 datum.
    <Format>
The essSubSurfaceSensorLatitude at the North Pole is 90,000,000. The essSubSurfaceSensorLatitude at the South Pole is -90,000,000. The value 90,000,001 shall indicate a missing value.
    <Parameter Type> configuration
    <Superseded by> essSubSurfaceSensorYOffset
    <Informative> This object was deprecated in version 05. 
    <Object Identifier> 1.3.6.1.4.1.1206.4.2.5.2.9.4.1.9"
  REFERENCE    "Resolution based on on-going location referencing activities; the WMO Binary Code Form FM 94 BUFR Table B item 0 05 001 can be obtained by dividing this value by 10."
::= { essSubSurfaceSensorEntry 9 }

-- 5.11.6.10 Subsurface Sensor Longitude
-- This object has been deprecated.
essSubSurfaceSensorLongitude OBJECT-TYPE
  SYNTAX       Integer32 (-180000000..180000001)
  UNITS        "microdegrees longitude"
  MAX-ACCESS   read-write
  STATUS       deprecated
  DESCRIPTION
    "<Definition> The east longitude in 10^-6 degrees from the Prime Meridian of the ESS subsurface sensor location. 
    <Format>
The essSubSurfaceSensorLongitude of 180 degrees West shall be -180,000,000. The essSubSurfaceSensorLongitude of 180 degrees East shall be 180,000,000. The value 180,000,001 shall indicate a missing value.
    <Parameter Type> configuration
    <Superseded by> essSubSurfaceSensorXOffset
    <Informative> This object was deprecated in version 05. 
    <Object Identifier> 1.3.6.1.4.1.1206.4.2.5.2.9.4.1.10"
  REFERENCE    "Resolution based on on-going location referencing activities; the WMO Binary Code Form FM 94 BUFR Table B item 0 06 001 can be obtained by dividing this value by 10."
::= { essSubSurfaceSensorEntry 10 }

-- 5.11.6.11 Subsurface Sensor Model Information
-- This object has been deprecated.
essSubSurfaceSensorModelInformation OBJECT-TYPE
  SYNTAX       Integer32 (0..255)
  MAX-ACCESS   read-write
  STATUS       deprecated
  DESCRIPTION
    "<Definition> Indicates the row in the Module Table (See NTCIP 1201) that contains information about the make, model, and version number of the sensor associated with this row of the SubSurface Sensor Table.
    <Format>
The value of zero indicates that this information is not available.
    <Parameter Type> configuration
    <Supplanted by> essSubSurfaceSensorEntityID
    <Informative> This object was deprecated in version 5. 
    <Object Identifier> 1.3.6.1.4.1.1206.4.2.5.2.9.4.1.11"
::= { essSubSurfaceSensorEntry 11 }

-- 5.11.6.12 Subsurface Sensor X Offset
essSubSurfaceSensorXOffset OBJECT-TYPE
  SYNTAX       ITSInteger16
  UNITS        "centimeters"
  MAX-ACCESS   read-write
  STATUS       current
  DESCRIPTION
    "<Definition> The offset latitude of the subsurface sensor from the field device's reference location as defined by fdConfiguredLatitude and fdConfiguredLongitude. 
    <Format>
For stationary devices, the X offset shall indicate the eastward (positive) or westward (negative) distance from the reference location. For transportable and mobile devices, the X offset shall indicate distances to the starboard side (positive) or port side (negative) of the reference location on the vehicle.
    <Parameter Type> configuration
    <Object Identifier> 1.3.6.1.4.1.1206.4.2.5.2.9.4.1.12"
::= { essSubSurfaceSensorEntry 12 }

-- 5.11.6.13 Subsurface Sensor Y Offset
essSubSurfaceSensorYOffset OBJECT-TYPE
  SYNTAX       ITSInteger16
  UNITS        "centimeters"
  MAX-ACCESS   read-write
  STATUS       current
  DESCRIPTION
    "<Definition> The Y offset of the subsurface sensor from the field device's reference location as defined by fdConfiguredLatitude and fdConfiguredLongitude. 
    <Format>
For stationary devices, the Y offset shall indicate the northward (positive) or southward (negative) distance from the reference location. For transportable and mobile devices, the Y offset shall indicate distances to the fore (positive) or aft (negative) of the reference location on the vehicle.
    <Parameter Type> configuration
    <Object Identifier> 1.3.6.1.4.1.1206.4.2.5.2.9.4.1.13"
::= { essSubSurfaceSensorEntry 13 }

-- 5.11.7 Pavement Block
-- This object has been deprecated.
essPavementBlock OBJECT-TYPE
  SYNTAX       ITSOerString
  MAX-ACCESS   read-only
  STATUS       deprecated
  DESCRIPTION
    "<Definition> An OER encoded string of the EssPavementData structure as defined below. This object is used for uploading current pavement data from the ESS in a bandwidth efficient manner.
    <Format>
The OPTIONAL fields shall be present if the data is supported by the 
implementation and is valid. The OPTIONAL fields shall be omitted for any 
data that is invalid or not supported by the implementation.


EssPavementData ::= SEQUENCE OF PavementSensorData
  -- for (
--  x = 1; 
--  x < numEssPavementSensors.0; 
--  x++)




PavementSensorData ::= SEQUENCE {
  essPavementSensorIndex.x    OPTIONAL, -- @NTCIP1204-Ess
  essSurfaceStatusV2.x      OPTIONAL, -- @NTCIP1204-Ess
  essSurfaceTemperature.x      OPTIONAL, -- @NTCIP1204-Ess
  essPavementTemperature.x    OPTIONAL, -- @NTCIP1204-Ess
  essSurfaceWaterDepth.x      OPTIONAL, -- @NTCIP1204-Ess
  essSurfaceSalinity.x      OPTIONAL, -- @NTCIP1204-Ess
  essSurfaceConductivity.x    OPTIONAL, -- @NTCIP1204-Ess
  essSurfaceFreezePoint.x      OPTIONAL, -- @NTCIP1204-Ess
  essSurfaceBlackIceSignal.x    OPTIONAL, -- @NTCIP1204-Ess
  essPavementSensorError.x    OPTIONAL  -- @NTCIP1204-Ess
}
    <Parameter Type> status
    <Superseded by> essPavementV3Block
    <Informative> This object was deprecated in version 03. 
    <Object Identifier> 1.3.6.1.4.1.1206.4.2.5.2.9.5"
::= { essNtcipPavement 5 }

-- 5.11.8 Subsurface Block Object
-- This object has been deprecated.
essSubSurfaceBlock OBJECT-TYPE
  SYNTAX       ITSOerString
  MAX-ACCESS   read-only
  STATUS       deprecated
  DESCRIPTION
    "<Definition> An OER encoded string of the EssSubsurfaceData structure as defined below. This object is used for uploading current subsurface data from the ESS in a bandwidth efficient manner.
    <Format>
The OPTIONAL fields shall be present if the data is supported by the 
implementation and is valid. The OPTIONAL fields shall be omitted for any 
data that is invalid or not supported by the implementation.


EssSubSurfaceData ::= SEQUENCE OF SubSurfaceSensorData
  -- for (
--  x = 1; 
--  x < numEssSubSurfaceSensors.0; 
--  x++)


SubSurfaceSensorData ::= SEQUENCE {
  essSubSurfaceSensorIndex.x    OPTIONAL, -- @NTCIP1204-Ess
  essSubSurfaceTemperature.x    OPTIONAL, -- @NTCIP1204-Ess
  essSubSurfaceMoisture.x      OPTIONAL, -- @NTCIP1204-Ess
  essSubSurfaceSensorError.x    OPTIONAL  -- @NTCIP1204-Ess
  }
    <Parameter Type> status
    <Withdrawn> 
    <Informative> This object was deprecated and withdrawn in version 05 as the associated requirement was deemed to be no longer necessary in version 04.
    <Object Identifier> 1.3.6.1.4.1.1206.4.2.5.2.9.6"
::= { essNtcipPavement 6 }

-- 5.11.9 Pavement Block V3
-- This object has been deprecated.
essPavementV3Block OBJECT-TYPE
  SYNTAX       ITSOerString
  MAX-ACCESS   read-only
  STATUS       deprecated
  DESCRIPTION
    "<Definition> An OER encoded string of the EssPavementDataV3 structure as defined below. This object is used for uploading current pavement data from the ESS in a bandwidth efficient manner.
    <Format>
The OPTIONAL fields shall be present if the data is supported by the 
implementation and is valid. The OPTIONAL fields shall be omitted for any 
data that is invalid or not supported by the implementation.


EssPavementDataV3 ::= SEQUENCE OF PavementSensorDataV3
  -- for (
--  x = 1; 
--  x < numEssPavementSensors.0; 
--  x++)




PavementSensorDataV3 ::= SEQUENCE {
  essPavementSensorIndex.x    OPTIONAL, -- @NTCIP1204-Ess
  essSurfaceStatus.x      OPTIONAL, -- @NTCIP1204-Ess
  essSurfaceTemperature.x      OPTIONAL, -- @NTCIP1204-Ess
  essPavementTemperature.x    OPTIONAL, -- @NTCIP1204-Ess
  essSurfaceSalinity.x      OPTIONAL, -- @NTCIP1204-Ess
  essSurfaceFreezePoint.x      OPTIONAL, -- @NTCIP1204-Ess
  essSurfaceBlackIceSignal.x    OPTIONAL, -- @NTCIP1204-Ess
  essPavementSensorError.x    OPTIONAL, -- @NTCIP1204-Ess
  essSurfaceIceOrWaterDepth.x    OPTIONAL, -- @NTCIP1204-Ess
  essSurfaceConductivityV2.x    OPTIONAL  -- @NTCIP1204-Ess
}
    <Parameter Type> status
    <Informative> This object was deprecated and withdrawn in NTCIP 1204 v04 as the associated requirement was deemed to be no longer necessary.
    <Object Identifier> 1.3.6.1.4.1.1206.4.2.5.2.9.7"
::= { essNtcipPavement 7 }

-- 5.12 Mobile Platform Objects
essNtcipMobile OBJECT-IDENTITY
    STATUS       current
  DESCRIPTION
    "<Definition> Objects related to monitoring mobile platforms that act as an ESS (e.g., specially-equipped maintenance vehicles). 
    <Object Identifier> 1.3.6.1.4.1.1206.4.2.5.2.10"
::= {essNtcip 10}

-- 5.12.1 Detected Friction
-- This object has been deprecated.
essMobileFriction OBJECT-TYPE
  SYNTAX       Integer32 (0..101)
  UNITS        "percent friction"
  MAX-ACCESS   read-only
  STATUS       deprecated
  DESCRIPTION
    "<Definition> Indicates measured coefficient of friction in percent.
    <Format>
The value 101 shall indicate an error condition or missing value.
    <Parameter Type> status
    <Superseded by> pavementSensorFrictionCoefficient
    <Informative> This object was deprecated in version 04.
    <Object Identifier> 1.3.6.1.4.1.1206.4.2.5.2.10.1"
::= { essNtcipMobile 1 }

-- 5.12.2 Observed Ground State
-- This object has been deprecated.
essMobileObservationGroundState OBJECT-TYPE
  SYNTAX       INTEGER {
    other (1),
    dry (2),
    moist (3),
    wet (4),
    flooded (5),
    frozen (6),
    glaze (7),
    dustySandy (8),
    veryDry (9),
    icy (10),
    patchyWetSnow (11),
    moderateWetSnowCover (12),
    fullWetSnowCover (13),
    patchyDrySnow (14),
    moderateDrySnowCover (15),
    fullDrySnowCover (16),
    driftingSnow (17),
    unknown (18) }
  MAX-ACCESS   read-only
  STATUS       deprecated
  DESCRIPTION
    "<Definition> The prevailing observed ground state of the surrounding environment as determined by the observer. This is an indicator of past weather conditions.
    <Parameter Type> status
    <Superseded by> essMobileObservationGroundStateV4
    <Informative> This object was deprecated in version 04.
    <Object Identifier> 1.3.6.1.4.1.1206.4.2.5.2.10.2"
::= { essNtcipMobile 2 }

-- 5.12.3 Observed Pavement State
-- This object has been deprecated.
essMobileObservationPavement OBJECT-TYPE
  SYNTAX       INTEGER {
    other (1),
    dry (2),
    wet (3),
    puddles (4),
    shallowStandingWater (5),
    shallowFlowingWater (6),
    deepStandingWater (7),
    deepFlowingWater (8),
    dustingFreshSnow (9),
    moderateFreshSnow (10),
    deepFreshSnow (11),
    plowedSnow (12),
    slush (13),
    packedSnowPatches (14),
    packedSnow (15),
    lightSnowDrifts (16),
    moderateSnowDrifts (17),
    heavySnowDrifts (18),
    frost (19),
    icePatches (20),
    moderatelyIcy (21),
    heavyIcing (22),
    blackIce (23),
    sheetIce (24),
    frozenSlush (25) }
  MAX-ACCESS   read-only
  STATUS       deprecated
  DESCRIPTION
    "<Definition> The prevailing observed conditions on the driving surface as determined by the observer.
    <Parameter Type> status
    <Superseded by> essMobileObservationPavementV4
    <Informative> This object was deprecated in version 04.
    <Object Identifier> 1.3.6.1.4.1.1206.4.2.5.2.10.3"
::= { essNtcipMobile 3 }

-- 5.12.4 Observed Ground State - Version 4
essMobileObservationGroundStateV4 OBJECT-TYPE
  SYNTAX       INTEGER {
    other (1),
    dry (2),
    moist (3),
    wet (4),
    flooded (5),
    frozen (6),
    glaze (7),
    dustySandy (8),
    veryDry (9),
    icy (10),
    patchyWetSnow (11),
    moderateWetSnowCover (12),
    fullWetSnowCover (13),
    patchyDrySnow (14),
    moderateDrySnowCover (15),
    fullDrySnowCover (16),
    driftingSnow (17),
    unknown (18),
   puddles (19),
   standingWater (20),
   flowingWater (21),
   freshSnow (22),
   plowedSnow (23),
   slush (24) }
  MAX-ACCESS   read-only
  STATUS       current
  DESCRIPTION
    "<Definition> The prevailing observed ground state of the surrounding environment as determined by the observer. This is an indicator of past weather conditions.
    <Parameter Type> status
    <Object Identifier> 1.3.6.1.4.1.1206.4.2.5.2.10.4"
::= { essNtcipMobile 4 }

-- 5.12.5 Observed Pavement State - Version 4
essMobileObservationPavementV4 OBJECT-TYPE
  SYNTAX       INTEGER {
    other (1),
    dry (2),
    wet (3),
    puddles (4),
    shallowStandingWater (5),
    shallowFlowingWater (6),
    deepStandingWater (7),
    deepFlowingWater (8),
    dustingFreshSnow (9),
    moderateFreshSnow (10),
    deepFreshSnow (11),
    plowedSnow (12),
    slush (13),
    packedSnowPatches (14),
    packedSnow (15),
    lightSnowDrifts (16),
    moderateSnowDrifts (17),
    heavySnowDrifts (18),
    frost (19),
    icePatches (20),
    moderatelyIcy (21),
    heavyIcing (22),
    blackIce (23),
    sheetIce (24),
    frozenSlush (25),
   absorption (26),
   absorptionAtDewpoint (27),
   bareAndDry (28),
   bareAndWet (29),
   blowingsnow (30),
   chemicallyWet (31),
   dew (32),
   damp (33),
   wetSlush (34) }
  MAX-ACCESS   read-only
  STATUS       current
  DESCRIPTION
    "<Definition> The prevailing observed conditions on the driving surface as determined by the observer.
    <Parameter Type> status
    <Object Identifier> 1.3.6.1.4.1.1206.4.2.5.2.10.5"
::= { essNtcipMobile 5 }

-- 5.13 Pavement Treatment Objects
essNtcipTreatment OBJECT-IDENTITY
    STATUS       current
  DESCRIPTION
    "<Definition> Objects that monitor the various types and amounts of treatments that are spread on the pavement surface.
    <Object Identifier> 1.3.6.1.4.1.1206.4.2.5.2.11"
::= { essNtcip 11 }

-- 5.13.1 Number of Treatments
numEssTreatments OBJECT-TYPE
  SYNTAX       Integer32 (0..255)
  UNITS        "treatments"
  MAX-ACCESS   read-only
  STATUS       current
  DESCRIPTION
    "<Definition> Indicates the number of entries in the Pavement Treatment Table.
    <Parameter Type> status
    <Object Identifier> 1.3.6.1.4.1.1206.4.2.5.2.11.1"
::= { essNtcipTreatment 1 }

-- 5.13.2 Pavement Treatment Table
essPavementTreatmentTable OBJECT-TYPE
  SYNTAX       SEQUENCE OF EssPavementTreatmentEntry
  MAX-ACCESS   not-accessible
  STATUS       current
  DESCRIPTION
    "<Definition> Table containing the pavement treatment data.
    <Object Identifier> 1.3.6.1.4.1.1206.4.2.5.2.11.2"
::= { essNtcipTreatment 2 }

-- 5.13.3 Pavement Treatment
essPavementTreatmentEntry OBJECT-TYPE
  SYNTAX       EssPavementTreatmentEntry
  MAX-ACCESS   not-accessible
  STATUS       current
  DESCRIPTION
    "<Definition> A pavement treatment is a chemical that can be applied to the roadway to de-ice or prevent icing of the pavement. It can be described through a number of attributes as indicated by the following subclauses."
  INDEX { essPavementTreatmentIndex }
::= { essPavementTreatmentTable 1 }

EssPavementTreatmentEntry ::= SEQUENCE {
  essPavementTreatmentIndex               Integer32,
  essPaveTreatProductType                 INTEGER,
  essPaveTreatProductForm                 INTEGER,
  essPercentProductMix                    Integer32}

-- 5.13.3.1 Pavement Treatment Index
essPavementTreatmentIndex OBJECT-TYPE
  SYNTAX       Integer32 (1..255)
  MAX-ACCESS   read-only
  STATUS       current
  DESCRIPTION
    "<Definition> Enumerated list of row entries that provide pavement treatment data.
    <Parameter Type> status
    <Object Identifier> 1.3.6.1.4.1.1206.4.2.5.2.11.2.1.1"
::= { essPavementTreatmentEntry 1 }

-- 5.13.3.2 Pavement Treatment Product Type
essPaveTreatProductType OBJECT-TYPE
  SYNTAX       INTEGER {
    other (1),
    sand (2),
    dirt (3),
    gravel (4),
    cinders (5),
    water (6),
    enhancedSalts (7),
    naCl (8),
    caCl (9),
    mgCl (10),
    cMA (11),
    kAC (12),
    naFormate (13),
    naA (14) }
  MAX-ACCESS   read-write
  STATUS       current
  DESCRIPTION
    "<Definition> Indicates the type of treatment being applied to the road. An enhanced definition of some of the values are as follows: other - any other type of treatment water - used as a diluting agent cMA - Calcium-Magnesium Acetate kAC - Potassium-Magnesium Acetate naFormate - Sodium Formate naA - Sodium Acetate
    <Format>
An enhanced definition of some of the values are as follows.
other - any other type of treatment
water - used as a diluting agent
cMA - Calcium-Magnesium Acetate
kAC - Potassium-Magnesium Acetate
naFormate - Sodium Formate
naA - Sodium Acetate
    <Parameter Type> configuration
    <Informative> Version 02 of this standard incorrectly defined the set constraint of this read-write object to be read-only; it should be always, however, the intent is that it would only be set by a local connection when the new product is being loaded and that remote systems would only read this object.
    <Object Identifier> 1.3.6.1.4.1.1206.4.2.5.2.11.2.1.2"
::= { essPavementTreatmentEntry 2 }

-- 5.13.3.3 Treatment Product Form
essPaveTreatProductForm OBJECT-TYPE
  SYNTAX       INTEGER {
    other (1),
    dry (2),
    prewet (3),
    liquid (4) }
  MAX-ACCESS   read-write
  STATUS       current
  DESCRIPTION
    "<Definition> Indicates the condition of the treatment being applied to the road.
    <Parameter Type> configuration
    <Informative> Version 02 and 03 of this standard incorrectly defined the set constraint of this read-write object to be read-only; it should be always, however, the intent is that it would only be set by a local connection when the new product is being loaded and that remote systems would only read this object.
    <Object Identifier> 1.3.6.1.4.1.1206.4.2.5.2.11.2.1.3"
::= { essPavementTreatmentEntry 3 }

-- 5.13.3.4 Percentage of Treatment Type in Mix
essPercentProductMix OBJECT-TYPE
  SYNTAX       Integer32 (0..100)
  UNITS        "percent"
  MAX-ACCESS   read-write
  STATUS       current
  DESCRIPTION
    "<Definition> Indicates the percentage of the total application mix by weight that is of the type specified in essPaveTreatProductType.
    <Format>
The sum of these percentages within the total mixture shall equal 100.
    <Parameter Type> configuration
    <Informative> Version 02 of this standard incorrectly defined the set constraint of this read-write object to be read-only; it should be always, however, the intent is that it would only be set by a local connection when the new product is being loaded and that remote systems would only read this object. 
    <Object Identifier> 1.3.6.1.4.1.1206.4.2.5.2.11.2.1.4"
::= { essPavementTreatmentEntry 4 }

-- 5.13.4 Treatment Amount
essPaveTreatmentAmount OBJECT-TYPE
  SYNTAX       Integer32 (0..255)
  UNITS        " kilograms per lane kilometer"
  MAX-ACCESS   read-write
  STATUS       current
  DESCRIPTION
    "<Definition> Indicates quantity of the treatment being applied in kilograms per lane kilometer.
    <Format>
The value of 255 shall indicate an error condition or missing value.
    <Parameter Type> configuration
    <Object Identifier> 1.3.6.1.4.1.1206.4.2.5.2.11.3"
::= { essNtcipTreatment 3 }

-- 5.13.5 Treatment Width
essPaveTreatmentWidth OBJECT-TYPE
  SYNTAX       Integer32 (0..255)
  UNITS        "meters"
  MAX-ACCESS   read-write
  STATUS       current
  DESCRIPTION
    "<Definition> Indicates the width of the spread of treatment in meters.
    <Format>
The value of 255 shall indicate an error condition or missing value.
    <Parameter Type> configuration
    <Object Identifier> 1.3.6.1.4.1.1206.4.2.5.2.11.4"
::= { essNtcipTreatment 4 }

-- 5.13.6 Pavement Treatment Block
-- This object has been deprecated.
pavementTreatmentBlock OBJECT-TYPE
  SYNTAX       ITSOerString
  MAX-ACCESS   read-only
  STATUS       deprecated
  DESCRIPTION
    "<Definition> An OER encoded string of the Pavement Treatment data. This object is used for uploading current pavement treatment data from the ESS in a bandwidth efficient manner.
    <Format>
The OPTIONAL fields shall be present if the data is supported by the 
implementation and is valid. The OPTIONAL fields shall be omitted for any 
data that is invalid or not supported by the implementation.



Note: The following structure contains pts data elements in addition to 
the ess data elements. Although these are not currently required to 
fulfill any existing requirements, they are included to maintain backward 
compatibility with the version 02 standard.


PavementTreatmentBlock ::= SEQUENCE {
  treatmentInfo  SEQUENCE OF PavementTreatmentData OPTIONAL,
  essPaveTreatmentAmount.0  OPTIONAL, -- @NTCIP1204-Ess
  essPaveTreatmentWidth.0    OPTIONAL, -- @NTCIP1204-Ess
  ptsOperationalMode.0    OPTIONAL, -- @NTCIP1204-Ess
  ptsCommandState.0      OPTIONAL, -- @NTCIP1204-Ess
  ptsSprayerState.0      OPTIONAL, -- @NTCIP1204-Ess
  ptsSignalDuration.0    OPTIONAL, -- @NTCIP1204-Ess
  ptsSignalEventCount.0    OPTIONAL, -- @NTCIP1204-Ess
  ptsLastSignalEvent.0    OPTIONAL, -- @NTCIP1204-Ess
  ptsActiveEventCount.0    OPTIONAL, -- @NTCIP1204-Ess
  ptsInactiveEventCount.0    OPTIONAL, -- @NTCIP1204-Ess
  ptsLastactiveEvent.0    OPTIONAL, -- @NTCIP1204-Ess
  ptsLastInactiveEvent.0    OPTIONAL, -- @NTCIP1204-Ess
  ptsError.0        OPTIONAL, -- @NTCIP1204-Ess
  ptsMonitoringDetectors.0  OPTIONAL  -- @NTCIP1204-Ess
}


PavementTreatmentData ::= 
  -- for (
  --  x = 1; 
  --  x < numEssTreatments.0; 
  --  x++)
SEQUENCE {
  essPavementTreatmentIndex.x    OPTIONAL, -- @NTCIP1204-Ess
  essPaveTreatProductType.x    OPTIONAL, -- @NTCIP1204-Ess
  essPaveTreatProductForm.x    OPTIONAL, -- @NTCIP1204-Ess
  essPercentProductMix.x      OPTIONAL  -- @NTCIP1204-Ess
}
    <Parameter Type> status
    <Informative> This object was deprecated and withdrawn in version 05 as the associated requirement was deemed to be no longer necessary in version 04.
    <Object Identifier> 1.3.6.1.4.1.1206.4.2.5.2.11.5"
::= { essNtcipTreatment 5 }

-- 5.13.7 Operational Mode [Obsolete]
-- This object is obsolete.
ptsOperationalMode OBJECT-TYPE
  SYNTAX       INTEGER {
    off (1),
    manual (2),
    automatic (3) }
  MAX-ACCESS   read-write
  STATUS       obsolete
  DESCRIPTION
    "<Definition> Indicates the operational mode of the Pavement Treatment System.
When in the 'off' state, the PTS shall not trigger the sprayer even if commanded to do so and shall always be inactive. The PTS shall transition to the requested operational mode, upon request.
When in the 'automatic' state, the PTS shall monitor conditions and trigger the sprayer based on a manufacturer specific algorithm. The algorithm shall only consider input from the detectors selected in the ptsMonitoringDetectors object. The PTS shall also trigger the sprayer if commanded to do so via the ptsCommandState object. The PTS shall transition to the requested operational mode, upon request.
When in the 'manual' state, the PTS shall trigger the sprayer if commanded to do so via the ptsCommandState object. The PTS shall transition to the requested operational mode, upon request.
    <Format>
off  When set to this value the ESS does not trigger the 
  bridge sprayer 

manual  When set to this value the ESS only triggers the 
  bridge sprayer when manually commanded to do
  so (e.g., see bridgeSprayerMgmtSignalState). 

automatic  When set to this value the ESS triggers the
  bridge sprayer when manually commanded to do 
  so or when the internal algorithm determines
  that the sprayer should be triggered.
    <Parameter Type> control
    <Superseded by> ptsOperationalModeV3
    <Informative> This object was made obsolete in version 03.
    <Object Identifier> 1.3.6.1.4.1.1206.4.2.5.2.11.6"
::= { essNtcipTreatment 6 }

-- 5.13.8 Command State [Obsolete]
-- This object is obsolete.
ptsCommandState OBJECT-TYPE
  SYNTAX       INTEGER {
    other (1),
    inactive (2),
    activate (3) }
  MAX-ACCESS   read-write
  STATUS       obsolete
  DESCRIPTION
    "<Definition> Indicates the operational state of the PTS. When in the 'inactive' state, the PTS shall not be spraying. Upon entering the 'active' state, either by a manual SET of this object or through an automated algorithm, the PTS shall trigger the sprayer and spray the chemical for a duration as defined by the ptsSignalDuration object. Upon expiration of this duration, the PTS shall automatically transition back to the 'inactive' state.
    <Format>
other - 
read  - indicates a unknown or initial state
write - no effect
inactive  - 
read  - indicates the ess is not signaling the bridge sprayer 
write - no effect
activate  - 
read  - indicates the ess is signaling the bridge sprayer      
write - causes the ess to signal the bridge sprayer
    <Parameter Type> control
    <Superseded by> ptsCommandStateV3
    <Informative> This object was made obsolete in version 03.
    <Object Identifier> 1.3.6.1.4.1.1206.4.2.5.2.11.7"
::= { essNtcipTreatment 7 }

-- 5.13.9 Sprayer State
ptsSprayerState OBJECT-TYPE
  SYNTAX       INTEGER {
    other (1),
    inactive (2),
    active (3) }
  MAX-ACCESS   read-only
  STATUS       current
  DESCRIPTION
    "<Definition> other     - indicates a unknown or initial state
             inactive  - indicates the bridge sprayer is inactive
             active    - indicates the bridge sprayer is active
    <Parameter Type> status
    <Object Identifier> 1.3.6.1.4.1.1206.4.2.5.2.11.8"
::= { essNtcipTreatment 8 }

-- 5.13.10 Signal Duration
ptsSignalDuration OBJECT-TYPE
  SYNTAX       Integer32 (0..3600000)
  UNITS        "milliseconds"
  MAX-ACCESS   read-write
  STATUS       current
  DESCRIPTION
    "<Definition> The number of milliseconds of a simple logic level or state the bridge sprayer needs to detect a signal from the ESS.
    <Parameter Type> configuration
    <Object Identifier> 1.3.6.1.4.1.1206.4.2.5.2.11.9"
::= { essNtcipTreatment 9 }

-- 5.13.11 Signal Event Count
ptsSignalEventCount OBJECT-TYPE
  SYNTAX       Counter32
  UNITS        "events"
  MAX-ACCESS   read-only
  STATUS       current
  DESCRIPTION
    "<Definition> An indication of the number of Signal Events that have occurred since the last SNMP engine initialization.
    <Parameter Type> status
    <Informative> SNMP counter objects do not have a defined initialization value nor any ability to be reset. The value reported by this object only has meaning when compared to a previous reading and when there is no intervening device initialization as indicated by snmpEngineBoots.
    <Object Identifier> 1.3.6.1.4.1.1206.4.2.5.2.11.10"
::= { essNtcipTreatment 10 }

-- 5.13.12 Last Signal Event
-- This object has been deprecated.
ptsLastSignalEvent OBJECT-TYPE
  SYNTAX       Unsigned32
  UNITS        "seconds"
  MAX-ACCESS   read-only
  STATUS       deprecated
  DESCRIPTION
    "<Definition> The number of seconds since 00:00:00 Jan 1 1970 UTC.
    <Format>
The value of 0 indicates an unknown or initial value.
    <Parameter Type> status
    <Superseded by> ptsLastSignalEventDate and ptsLastSignalEventTime
    <Informative> This object was deprecated in version 05.
Within SNMPv1, this object was represented as a Counter in violation of Counter semantics. Within SNMPv3 exchanges, it is encoded as an Unsigned32 to conform to SMIv2 and SNMPv3 rules.
    <Object Identifier> 1.3.6.1.4.1.1206.4.2.5.2.11.11"
::= { essNtcipTreatment 11 }

-- 5.13.13 Active Event Count
ptsActiveEventCount OBJECT-TYPE
  SYNTAX       Counter32
  UNITS        "events"
  MAX-ACCESS   read-only
  STATUS       current
  DESCRIPTION
    "<Definition> An indication of the number of Active Events that have occurred since the last SNMP engine initialization.
    <Parameter Type> status
    <Informative> SNMP counter objects do not have a defined initialization value nor any ability to be reset. The value reported by this object only has meaning when compared to a previous reading and when there is no intervening device initialization as indicated by snmpEngineBoots.
    <Object Identifier> 1.3.6.1.4.1.1206.4.2.5.2.11.12"
::= { essNtcipTreatment 12 }

-- 5.13.14 Inactive Event Count
ptsInactiveEventCount OBJECT-TYPE
  SYNTAX       Counter32
  UNITS        "events"
  MAX-ACCESS   read-only
  STATUS       current
  DESCRIPTION
    "<Definition> An indication of the number of Inactive Events that have occurred since the last SNMP engine initialization.
    <Parameter Type> status
    <Informative> SNMP counter objects do not have a defined initialization value nor any ability to be reset. The value reported by this object only has meaning when compared to a previous reading and when there is no intervening device initialization as indicated by snmpEngineBoots.
    <Object Identifier> 1.3.6.1.4.1.1206.4.2.5.2.11.13"
::= { essNtcipTreatment 13 }

-- 5.13.15 Last Active Event
-- This object has been deprecated.
ptsLastActiveEvent OBJECT-TYPE
  SYNTAX       Unsigned32
  UNITS        "seconds"
  MAX-ACCESS   read-only
  STATUS       deprecated
  DESCRIPTION
    "<Definition> The number of seconds since 00:00:00 Jan 1 1970 UTC.
    <Format>
The value of 0 indicates an unknown or initial value.
    <Parameter Type> status
    <Superseded by> ptsLastActiveEventDate and ptsLastActiveEventTime
    <Informative> This object was deprecated in version 05.
Within SNMPv1, this object was represented as a Counter in violation of Counter semantics. Within SNMPv3 exchanges, it is encoded as an Unsigned32 to conform to SMIv2 and SNMPv3 rules.
    <Object Identifier> 1.3.6.1.4.1.1206.4.2.5.2.11.14"
::= { essNtcipTreatment 14 }

-- 5.13.16 Last Inactive Event
-- This object has been deprecated.
ptsLastInactiveEvent OBJECT-TYPE
  SYNTAX       Counter32
  UNITS        "seconds"
  MAX-ACCESS   read-only
  STATUS       deprecated
  DESCRIPTION
    "<Definition> The number of seconds since 00:00:00 Jan 1 1970 UTC.
    <Format>
The value of 0 indicates an unknown or initial value.
    <Parameter Type> status
    <Superseded by> ptsLastInactiveEventDate and ptsLastInactiveEventTime
    <Informative> This object was deprecated in version 05.
Within SNMPv1, this object was represented as a Counter in violation of Counter semantics. Within SNMPv3 exchanges, it is encoded as an Unsigned32 to conform to SMIv2 and SNMPv3 rules.
    <Object Identifier> 1.3.6.1.4.1.1206.4.2.5.2.11.15"
::= { essNtcipTreatment 15 }

-- 5.13.17 PTS Error Code
ptsError OBJECT-TYPE
  SYNTAX       INTEGER {
    other (1),
    ok (2),
    genericError (3),
    tankLow (4) }
  MAX-ACCESS   read-only
  STATUS       current
  DESCRIPTION
    "<Definition> Indicates the status of the bridge sprayer.
    <Format>
other        - indicates a unknown or initial state
ok           - indicates the bridge sprayer is operational
genericError - indicates the bridge sprayer has an error
tankLow      - indicates the bridge sprayer's tank is low
    <Parameter Type> status
    <Object Identifier> 1.3.6.1.4.1.1206.4.2.5.2.11.16"
::= { essNtcipTreatment 16 }

-- 5.13.18 Monitoring Detectors
ptsMonitoringDetectors OBJECT-TYPE
  SYNTAX       OCTET STRING (SIZE (4))
  MAX-ACCESS   read-write
  STATUS       current
  DESCRIPTION
    "<Definition> Indicates the pavement detectors that the PTS shall use in its algorithm that determines when the PTS automatically triggers the sprayer.
    <Format>
Each bit indicates whether or not the associated pavement sensor shall be used within the algorithm. The first (high order) bit in the bit string shall reference the first pavement sensor. A value of one for any bit shall indicate that the sensor input shall be considered, and a value of zero shall mean that the input shall not be considered.
    <Parameter Type> configuration
    <Object Identifier> 1.3.6.1.4.1.1206.4.2.5.2.11.17"
::= { essNtcipTreatment 17 }

-- 5.13.19 Operational Mode - Version 3
ptsOperationalModeV3 OBJECT-TYPE
  SYNTAX       INTEGER {
    off (1),
    manual (2),
    automatic (3) }
  MAX-ACCESS   read-write
  STATUS       current
  DESCRIPTION
    "<Definition> Indicates the operational mode of the Pavement Treatment System.
When in the 'off' state, the PTS shall not trigger the sprayer even if commanded to do so and shall always be inactive. The PTS shall transition to the requested operational mode, upon request.
When in the 'automatic' state, the PTS shall monitor conditions and trigger the sprayer based on a manufacturer specific algorithm. The algorithm shall only consider input from the detectors selected in the ptsMonitoringDetectors object. The PTS shall also trigger the sprayer if commanded to do so via the ptsCommandStateV3 object. The PTS shall transition to the requested operational mode, upon request.
When in the 'manual' state, the PTS shall trigger the sprayer if commanded to do so via the ptsCommandStateV3 object. The PTS shall transition to the requested operational mode, upon request.
    <Format>
off  When set to this value the ESS does not trigger the 
  bridge sprayer 

manual  When set to this value the ESS only triggers the 
  bridge sprayer when manually commanded to do
  so (e.g., see ptsCommandStateV3). 

automatic  When set to this value the ESS triggers the
  bridge sprayer when manually commanded to do 
  so or when the internal algorithm determines
  that the sprayer should be triggered.
    <Parameter Type> configuration
    <Object Identifier> 1.3.6.1.4.1.1206.4.2.5.2.11.18"
::= { essNtcipTreatment 18 }

-- 5.13.20 Command State - Version 3
ptsCommandStateV3 OBJECT-TYPE
  SYNTAX       INTEGER {
    other (1),
    inactive (2),
    activate (3) }
  MAX-ACCESS   read-write
  STATUS       current
  DESCRIPTION
    "<Definition> Indicates the operational state of the PTS. When in the 'inactive' state, the PTS shall not be signaling the sprayer. Upon entering the 'active' state, either by a manual SET of this object or through an automated algorithm, the PTS shall trigger the sprayer using a signal that lasts for a duration as defined by the ptsSignalDuration object. Upon expiration of this duration, the PTS shall automatically transition back to the 'inactive' state.
    <Format>
other - 
read  - indicates a unknown or initial state
write - no effect
inactive  - 
read  - indicates the ess is not signaling the bridge sprayer 
write - no effect
activate  - 
read  - indicates the ess is signaling the bridge sprayer      
write - causes the ess to signal the bridge sprayer
    <Parameter Type> control
    <Informative> This object does not directly control the sprayer, rather it merely signals an external sprayer.
    <Object Identifier> 1.3.6.1.4.1.1206.4.2.5.2.11.19"
::= { essNtcipTreatment 19 }

-- 5.13.21 PTS Latitude
-- This object has been deprecated.
essPavementTreatmentLatitude OBJECT-TYPE
  SYNTAX       Integer32 (-90000000..90000001)
  UNITS        "microdegrees latitude"
  MAX-ACCESS   read-write
  STATUS       deprecated
  DESCRIPTION
    "<Definition> The latitude in 10^-6 degrees of the pavement treatment system, per WGS-84 datum. 
    <Format>
The essPavementTreatmentLatitude at the North Pole is 90,000,000. The essPavementTreatmentLatitude at the South Pole is -90,000,000. The value 90,000,001 shall indicate a missing value.
    <Parameter Type> configuration
    <Superseded by> essPavementTreatmentYOffset
    <Informative> This object was deprecated in version 05. 
    <Object Identifier> 1.3.6.1.4.1.1206.4.2.5.2.11.20"
  REFERENCE    "Resolution based on on-going location referencing activities; the WMO Binary Code Form FM 94 BUFR Table B item 0 05 001 can be obtained by dividing this value by 10."
::= { essNtcipTreatment 20 }

-- 5.13.22 PTS Longitude
-- This object has been deprecated.
essPavementTreatmentLongitude OBJECT-TYPE
  SYNTAX       Integer32 (-180000000..180000001)
  UNITS        "microdegrees longitude"
  MAX-ACCESS   read-write
  STATUS       deprecated
  DESCRIPTION
    "<Definition> The east longitude in 10^-6 degrees from the Prime Meridian of the pavement treatment system location. 
    <Format>
The essPavementTreatmentLongitude of 180 degrees West shall be -180,000,000. The essPavementTreatmentLongitude of 180 degrees East shall be 180,000,000. The value 180,000,001 shall indicate a missing value.
    <Parameter Type> configuration
    <Superseded by> essPavementTreatmentXOffset
    <Informative> This object was deprecated in version 05. 
    <Object Identifier> 1.3.6.1.4.1.1206.4.2.5.2.11.21"
  REFERENCE    "Resolution based on on-going location referencing activities; the WMO Binary Code Form FM 94 BUFR Table B item 0 06 001 can be obtained by dividing this value by 10."
::= { essNtcipTreatment 21 }

-- 5.13.23 PTS Location
essPavementTreatmentLocation OBJECT-TYPE
  SYNTAX       SnmpAdminString
  MAX-ACCESS   read-write
  STATUS       current
  DESCRIPTION
    "<Definition> A textual string indicating the location of the pavement treatment system.
    <Parameter Type> configuration
    <Object Identifier> 1.3.6.1.4.1.1206.4.2.5.2.11.22"
::= { essNtcipTreatment 22 }

-- 5.13.24 PTS Model Information
-- This object has been deprecated.
essPavementTreatmentModelInformation OBJECT-TYPE
  SYNTAX       Integer32 (0..255)
  MAX-ACCESS   read-write
  STATUS       deprecated
  DESCRIPTION
    "<Definition> Indicates the row in the Module Table (See NTCIP 1201) that contains information about the make, model, and version number of the pavement treatment system.
    <Format>
The value of zero indicates that this information is not available.
    <Parameter Type> configuration
    <Superseded by> ptsEntityID
    <Informative> This object was deprecated in version 05. 
    <Object Identifier> 1.3.6.1.4.1.1206.4.2.5.2.11.23"
::= { essNtcipTreatment 23 }

-- 5.13.25 PTS Last Signal Event Time
ptsLastSignalEventTime OBJECT-TYPE
  SYNTAX       ITSTimeStamp
  MAX-ACCESS   read-only
  STATUS       current
  DESCRIPTION
    "<Definition> The number of milliseconds after 00:00:00.000 UTC on ptsLastSignalEventDate that the last signal event occurred.
    <Parameter Type> status
    <Object Identifier> 1.3.6.1.4.1.1206.4.2.5.2.11.24"
::= { essNtcipTreatment 24 }

-- 5.13.26 PTS Last Active Event Time
ptsLastActiveEventTime OBJECT-TYPE
  SYNTAX       ITSTimeStamp
  MAX-ACCESS   read-only
  STATUS       current
  DESCRIPTION
    "<Definition> The number of milliseconds after 00:00:00.000 UTC on ptsLastActiveEventDate that the last active event occurred.
    <Parameter Type> status
    <Object Identifier> 1.3.6.1.4.1.1206.4.2.5.2.11.25"
::= { essNtcipTreatment 25 }

-- 5.13.27 PTS Last Inactive Event Time
ptsLastInactiveEventTime OBJECT-TYPE
  SYNTAX       ITSTimeStamp
  MAX-ACCESS   read-only
  STATUS       current
  DESCRIPTION
    "<Definition> The number of milliseconds after 00:00:00.000 UTC on ptsLastActiveEventDate that the last inactive event occurred.
    <Parameter Type> status
    <Object Identifier> 1.3.6.1.4.1.1206.4.2.5.2.11.26"
::= { essNtcipTreatment 26 }

-- 5.13.28 PTS X Offset
ptsXOffset OBJECT-TYPE
  SYNTAX       ITSInteger16
  UNITS        "centimeters"
  MAX-ACCESS   read-write
  STATUS       current
  DESCRIPTION
    "<Definition> The lateral offset of the pavement treatment system from the field device's reference location as defined by fdConfiguredLatitude and fdConfiguredLongitude. 
    <Format>
For stationary devices, the X offset shall indicate the eastward (positive) or westward (negative) distance from the reference location. For transportable and mobile devices, the X offset shall indicate distances to the starboard side (positive) or port side (negative) of the reference location on the vehicle.
    <Parameter Type> configuration
    <Object Identifier> 1.3.6.1.4.1.1206.4.2.5.2.11.27"
::= { essNtcipTreatment 27 }

-- 5.13.29 PTS Y Offset
ptsYOffset OBJECT-TYPE
  SYNTAX       ITSInteger16
  UNITS        "centimeters"
  MAX-ACCESS   read-write
  STATUS       current
  DESCRIPTION
    "<Definition> The Y offset of the pavement treatment system from the field device's reference location as defined by fdConfiguredLatitude and fdConfiguredLongitude. 
    <Format>
For stationary devices, the Y offset shall indicate the northward (positive) or southward (negative) distance from the reference location. For transportable and mobile devices, the Y offset shall indicate distances to the fore (positive) or aft (negative) of the reference location on the vehicle.
    <Parameter Type> configuration
    <Object Identifier> 1.3.6.1.4.1.1206.4.2.5.2.11.28"
::= { essNtcipTreatment 28 }

-- 5.13.30 PTS Entity Identifier
ptsEntityID OBJECT-TYPE
  SYNTAX       PhysicalIndexOrZero
  MAX-ACCESS   read-only
  STATUS       current
  DESCRIPTION
    "<Definition> Indicates the row in the entPhysicalTable (See RFC 4133) that contains information about the pavement treatment system, such as the manufacturer, model, and hardware and software revision identifiers. 
    <Format>
The value of zero indicates that this information is not available.
    <Parameter Type> status
    <Informative> The mechanism used to configure this value when adding or modifying a sensor is not defined by this document and is considered manufacturer-specific.
    <Object Identifier> 1.3.6.1.4.1.1206.4.2.5.2.11.29"
::= { essNtcipTreatment 29 }

-- 5.14 Air Quality Parameters
essNtcipAirQuality OBJECT-IDENTITY
    STATUS       current
  DESCRIPTION
    "<Definition> Objects used for monitoring air quality conditions.
    <Object Identifier> 1.3.6.1.4.1.1206.4.2.5.2.12"
::= { essNtcip 12 }

-- 5.14.1 Carbon Monoxide Parameter
essCO OBJECT-TYPE
  SYNTAX       Integer32 (0..255)
  UNITS        "parts per million"
  MAX-ACCESS   read-only
  STATUS       current
  DESCRIPTION
    "<Definition> The concentration of carbon monoxide in the air, measured in parts per million.
    <Format>
The value 255 shall indicate an error condition or missing value.
    <Parameter Type> status
    <Object Identifier> 1.3.6.1.4.1.1206.4.2.5.2.12.1"
::= { essNtcipAirQuality 1 }

-- 5.14.2 Carbon Dioxide Parameter
-- This object has been deprecated.
essCO2 OBJECT-TYPE
  SYNTAX       Integer32 (0..65535)
  UNITS        "parts per billion"
  MAX-ACCESS   read-only
  STATUS       deprecated
  DESCRIPTION
    "<Definition> The concentration of carbon dioxide in the air, measured in parts per billion.
    <Format>
The value 65535 shall indicate an error condition or missing value.
    <Parameter Type> status
    <Superseded by> essCO2V4
    <Informative> This object was deprecated in version 04. 
    <Object Identifier> 1.3.6.1.4.1.1206.4.2.5.2.12.2"
::= { essNtcipAirQuality 2 }

-- 5.14.3 Nitrous Oxide Parameter
-- This object has been deprecated.
essNO OBJECT-TYPE
  SYNTAX       Integer32 (0..255)
  UNITS        "parts per million"
  MAX-ACCESS   read-only
  STATUS       deprecated
  DESCRIPTION
    "<Definition> The concentration of nitrous oxide in the air, measured in parts per million.
    <Format>
The value 255 shall indicate an error condition or missing value.
    <Parameter Type> status
    <Superseded by> essNOV4
    <Informative> This object was deprecated in version 04. 
    <Object Identifier> 1.3.6.1.4.1.1206.4.2.5.2.12.3"
::= { essNtcipAirQuality 3 }

-- 5.14.4 Nitrogen Dioxide Parameter
essNO2 OBJECT-TYPE
  SYNTAX       Integer32 (0..255)
  UNITS        "parts per billion"
  MAX-ACCESS   read-only
  STATUS       current
  DESCRIPTION
    "<Definition> The concentration of nitrogen dioxide in the air, measured in parts per billion. 
    <Format>
The value 255 shall indicate an error condition or missing value.
    <Parameter Type> status
    <Object Identifier> 1.3.6.1.4.1.1206.4.2.5.2.12.4"
::= { essNtcipAirQuality 4 }

-- 5.14.5 Sulfur Dioxide Parameter
essSO2 OBJECT-TYPE
  SYNTAX       Integer32 (0..65535)
  UNITS        "parts per billion"
  MAX-ACCESS   read-only
  STATUS       current
  DESCRIPTION
    "<Definition> The concentration of sulfur dioxide in the air, measured in parts per billion.
    <Format>
The value 65535 shall indicate an error condition or missing value.
    <Parameter Type> status
    <Object Identifier> 1.3.6.1.4.1.1206.4.2.5.2.12.5"
::= { essNtcipAirQuality 5 }

-- 5.14.6 Ozone Parameter
-- This object has been deprecated.
essO3 OBJECT-TYPE
  SYNTAX       Integer32 (0..255)
  UNITS        "parts per one hundred billion"
  MAX-ACCESS   read-only
  STATUS       deprecated
  DESCRIPTION
    "<Definition> The concentration of ozone in the air, measured in parts per one hundred billion.
    <Format>
The value 255 shall indicate an error condition or missing value.
    <Parameter Type> status
    <Superseded by> essO3V4
    <Informative> This object was deprecated in version 04. 
    <Object Identifier> 1.3.6.1.4.1.1206.4.2.5.2.12.6"
::= { essNtcipAirQuality 6 }

-- 5.14.7 Particulate Matter Parameter
essPM10 OBJECT-TYPE
  SYNTAX       Integer32 (0..65535)
  UNITS        "micrograms per cubic meter"
  MAX-ACCESS   read-only
  STATUS       current
  DESCRIPTION
    "<Definition> The concentration of small particulate matter of 10 micrometers or less in diameter in the air, measured in micrograms per cubic meter.
    <Format>
The value 65535 shall indicate an error condition or missing value.
    <Parameter Type> status
    <Object Identifier> 1.3.6.1.4.1.1206.4.2.5.2.12.7"
::= { essNtcipAirQuality 7 }

-- 5.14.8 Air Quality Block Object
-- This object has been deprecated.
essAirQualityBlock OBJECT-TYPE
  SYNTAX       ITSOerString
  MAX-ACCESS   read-only
  STATUS       deprecated
  DESCRIPTION
    "<Definition> An OER encoded string of the EssAirQualityData structure as defined below. 
This object is used for uploading current air quality data from the ESS in a 
bandwidth efficient manner.

A GET shall return data for all of the fields in the structure (even if they 
are indicated as OPTIONAL); unless the data values are not supported by the 
controller or are invalid (e.g., the sensor is not attached), in which case 
the values shall be omitted.

essAirQualityData ::= SEQUENCE {
  essCO.0        OPTIONAL,  -- @NTCIP1204-Ess
  essCO2.0        OPTIONAL,  -- @NTCIP1204-Ess
  essNO.0        OPTIONAL,  -- @NTCIP1204-Ess
  essNO2.0        OPTIONAL,  -- @NTCIP1204-Ess
  essSO2.0        OPTIONAL,  -- @NTCIP1204-Ess
  essO3.0        OPTIONAL,  -- @NTCIP1204-Ess
  essPM10.0        OPTIONAL  -- @NTCIP1204-Ess
  }
    <Parameter Type> status
    <Informative> This object was deprecated and withdrawn in version 05 as the associated requirement was deemed to be no longer necessary in version 04.
    <Object Identifier> 1.3.6.1.4.1.1206.4.2.5.2.12.8"
::= { essNtcipAirQuality 8 }

-- 5.14.9 Particulate Matter (2.5) Parameter
essPM25 OBJECT-TYPE
  SYNTAX       Integer32 (0..65535)
  UNITS        "micrograms per cubic meter"
  MAX-ACCESS   read-only
  STATUS       current
  DESCRIPTION
    "<Definition> The concentration of small particulate matter of 2.5 micrometers or less in diameter in the air, measured in micrograms per cubic meter.
    <Format>
The value 65535 shall indicate an error condition or missing value.
    <Parameter Type> status
    <Object Identifier> 1.3.6.1.4.1.1206.4.2.5.2.12.9"
::= { essNtcipAirQuality 9 }

-- 5.14.10 Number of Air Quality Sensors
airQualitySensorTableNumSensors OBJECT-TYPE
  SYNTAX       Integer32 (0..255)
  UNITS        "sensors"
  MAX-ACCESS   read-only
  STATUS       current
  DESCRIPTION
    "<Definition> Indicates the number of entries in the air quality sensor table.
    <Parameter Type> status
    <Informative> This value may automatically change upon connecting or disconnecting a sensor; however, the table is still defined as a static table since the creation/deletion of rows is not managed through SNMP logic.
    <Object Identifier> 1.3.6.1.4.1.1206.4.2.5.2.12.10"
::= { essNtcipAirQuality 10 }

-- 5.14.11 Air Quality Sensor Table
airQualitySensorTable OBJECT-TYPE
  SYNTAX       SEQUENCE OF AirQualitySensorEntry
  MAX-ACCESS   not-accessible
  STATUS       current
  DESCRIPTION
    "<Definition> Table containing the air quality sensor data.
    <Object Identifier> 1.3.6.1.4.1.1206.4.2.5.2.12.11"
::= { essNtcipAirQuality 11 }

-- 5.14.12 Air Quality Sensor
airQualitySensorEntry OBJECT-TYPE
  SYNTAX       AirQualitySensorEntry
  MAX-ACCESS   not-accessible
  STATUS       current
  DESCRIPTION
    "<Definition> An air quality sensor is described through a number of attributes as indicated by the following subclauses."
  INDEX { airQualitySensorIndex }
::= { airQualitySensorTable 1 }

AirQualitySensorEntry ::= SEQUENCE {
    airQualitySensorIndex             Integer32,
    airQualitySensorHeight            Integer32,
    airQualitySensorLatitude          Integer32,
    airQualitySensorLongitude         Integer32,
    airQualitySensorLocation          SnmpAdminString,
    airQualitySensorModelInformation  Integer32,
    airQualitySensorXOffset           ITSInteger16,
    airQualitySensorYOffset           ITSInteger16,
    airQualitySensorZOffset           ITSInteger16,
    airQualitySensorEntityID          PhysicalIndexOrZero }

-- 5.14.12.1 Air Quality Sensor Index
airQualitySensorIndex OBJECT-TYPE
  SYNTAX       Integer32 (1..255)
  MAX-ACCESS   read-only
  STATUS       current
  DESCRIPTION
    "<Definition> Enumerated list of row entries that provide air quality sensor data.
    <Parameter Type> status
    <Object Identifier> 1.3.6.1.4.1.1206.4.2.5.2.12.11.1.1"
::= { airQualitySensorEntry 1 }

-- 5.14.12.2 Air Quality Sensor Height
-- This object has been deprecated.
airQualitySensorHeight OBJECT-TYPE
  SYNTAX       Integer32 (-1000..1001)
  UNITS        "meters"
  MAX-ACCESS   read-write
  STATUS       deprecated
  DESCRIPTION
    "<Definition> The height of the air quality sensor with respect to the essReferenceHeight in meters.
    <Format>
The value of 1001 shall indicate a missing value.
    <Parameter Type> configuration
    <Superseded by> airQualitySensorZOffset
    <Informative> This object was deprecated in version 05. 
    <Object Identifier> 1.3.6.1.4.1.1206.4.2.5.2.12.11.1.2"
  REFERENCE    "essReferenceHeight plus this value equals the WMO Binary Code Form FM 94 BUFR Table B item 0 07 001."
::= { airQualitySensorEntry 2 }

-- 5.14.12.3 Air Quality Sensor Latitude
-- This object has been deprecated.
airQualitySensorLatitude OBJECT-TYPE
  SYNTAX       Integer32 (-90000000..90000001)
  UNITS        "microdegrees latitude"
  MAX-ACCESS   read-write
  STATUS       deprecated
  DESCRIPTION
    "<Definition> The latitude in 10^-6 degrees of the ESS air quality sensor, per WGS-84 datum.
    <Format>
The airQualitySensorLatitude at the North Pole is 90,000,000. The airQualitySensorLatitude at the South Pole is -90,000,000. The value 90,000,001 shall indicate a missing value.
    <Parameter Type> configuration
    <Superseded by> airQualitySensorYOffset
    <Informative> This object was deprecated in version 05. 
    <Object Identifier> 1.3.6.1.4.1.1206.4.2.5.2.12.11.1.3"
  REFERENCE    "Resolution based on on-going location referencing activities; the WMO Binary Code Form FM 94 BUFR Table B item 0 05 001 can be obtained by dividing this value by 10."
::= { airQualitySensorEntry 3 }

-- 5.14.12.4 Air Quality Sensor Longitude
-- This object has been deprecated.
airQualitySensorLongitude OBJECT-TYPE
  SYNTAX       Integer32 (-180000000..180000001)
  UNITS        "microdegrees longitude"
  MAX-ACCESS   read-write
  STATUS       deprecated
  DESCRIPTION
    "<Definition> The east longitude in 10^-6 degrees from the Prime Meridian of the ESS air quality sensor location.
    <Format>
The airQualityLongitude of 180 degrees West shall be -180,000,000. The airQualityLongitude of 180 degrees East shall be 180,000,000. The value 180,000,001 shall indicate a missing value.
    <Parameter Type> configuration
    <Superseded by> airQualitySensorXOffset
    <Informative> This object was deprecated in version 05. 
    <Object Identifier> 1.3.6.1.4.1.1206.4.2.5.2.12.11.1.4"
  REFERENCE    "Resolution based on on-going location referencing activities; the WMO Binary Code Form FM 94 BUFR Table B item 0 06 001 can be obtained by dividing this value by 10."
::= { airQualitySensorEntry 4 }

-- 5.14.12.5 Air Quality Sensor Location
airQualitySensorLocation OBJECT-TYPE
  SYNTAX       SnmpAdminString
  MAX-ACCESS   read-write
  STATUS       current
  DESCRIPTION
    "<Definition> A textual string indicating the location of the air quality sensor.
    <Parameter Type> configuration
    <Object Identifier> 1.3.6.1.4.1.1206.4.2.5.2.12.11.1.5"
::= { airQualitySensorEntry 5 }

-- 5.14.12.6 Air Quality Sensor Model Information
-- This object has been deprecated.
airQualitySensorModelInformation OBJECT-TYPE
  SYNTAX       Integer32(0..255)
  MAX-ACCESS   read-write
  STATUS       deprecated
  DESCRIPTION
    "<Definition> Indicates the row in the Module Table (See NTCIP 1201) that contains information about the make, model, and version number of the sensor associated with this row of the AirQuality Sensor Table.
    <Format>
The value of zero indicates that this information is not available.
    <Parameter Type> configuration
    <Supplanted by> airQualitySensorEntityID
    <Informative> This object was deprecated in version 05.
    <Object Identifier> 1.3.6.1.4.1.1206.4.2.5.2.12.11.1.6"
::= { airQualitySensorEntry 6 }

-- 5.14.12.7 Air Quality Sensor X Offset
airQualitySensorXOffset OBJECT-TYPE
  SYNTAX       ITSInteger16
  UNITS        "centimeters"
  MAX-ACCESS   read-write
  STATUS       current
  DESCRIPTION
    "<Definition> The lateral offset of the air quality sensor from the field device's reference location as defined by fdConfiguredLatitude and fdConfiguredLongitude. 
    <Format>
For stationary devices, the X offset shall indicate the eastward (positive) or westward (negative) distance from the reference location. For transportable and mobile devices, the X offset shall indicate distances to the starboard side (positive) or port side (negative) of the reference location on the vehicle.
    <Parameter Type> configuration
    <Object Identifier> 1.3.6.1.4.1.1206.4.2.5.2.12.11.1.7"
::= { airQualitySensorEntry 7 }

-- 5.14.12.8 Air Quality Sensor Y Offset
airQualitySensorYOffset OBJECT-TYPE
  SYNTAX       ITSInteger16
  UNITS        "centimeters"
  MAX-ACCESS   read-write
  STATUS       current
  DESCRIPTION
    "<Definition> The Y offset of the air quality sensor from the field device's reference location as defined by fdConfiguredLatitude and fdConfiguredLongitude. 
    <Format>
For stationary devices, the Y offset shall indicate the northward (positive) or southward (negative) distance from the reference location. For transportable and mobile devices, the Y offset shall indicate distances to the fore (positive) or aft (negative) of the reference location on the vehicle.
    <Parameter Type> configuration
    <Object Identifier> 1.3.6.1.4.1.1206.4.2.5.2.12.11.1.8"
::= { airQualitySensorEntry 8 }

-- 5.14.12.9 Air Quality Sensor Z Offset
airQualitySensorZOffset OBJECT-TYPE
  SYNTAX       ITSInteger16
  UNITS        "centimeters"
  MAX-ACCESS   read-write
  STATUS       current
  DESCRIPTION
    "<Definition> The offset elevation of the air quality sensor from the fdConfiguredElevation in centimeters.
    <Format>
Upward offsets shall be positive and downward offsets shall be negative. 
    <Parameter Type> configuration
    <Object Identifier> 1.3.6.1.4.1.1206.4.2.5.2.12.11.1.9"
::= { airQualitySensorEntry 9 }

-- 5.14.12.10 Air Quality Sensor Entity Identifier
airQualitySensorEntityID OBJECT-TYPE
  SYNTAX       PhysicalIndexOrZero
  MAX-ACCESS   read-only
  STATUS       current
  DESCRIPTION
    "<Definition> Indicates the row in the entPhysicalTable (See RFC 4133) that contains information about the sensor, such as the manufacturer, model, and hardware and software revision identifiers. 
    <Format>
The value of zero indicates that this information is not available.
    <Parameter Type> status
    <Informative> The mechanism used to configure this value when adding or modifying a sensor is not defined by this document and is considered manufacturer-specific.
    <Object Identifier> 1.3.6.1.4.1.1206.4.2.5.2.12.11.1.10"
::= { airQualitySensorEntry 10 }

-- 5.14.13 Carbon Dioxide Version 4 Parameter
essCO2V4 OBJECT-TYPE
  SYNTAX       Integer32 (0..65535)
  UNITS        "parts per million"
  MAX-ACCESS   read-only
  STATUS       current
  DESCRIPTION
    "<Definition> The concentration of carbon dioxide in the air, measured in parts per million.
    <Format>
The value 65535 shall indicate an error condition or missing value. 
    <Parameter Type> status
    <Object Identifier> 1.3.6.1.4.1.1206.4.2.5.2.12.13"
::= { essNtcipAirQuality 13 }

-- 5.14.14 Nitric Oxide Version 4 Parameter
essNOV4 OBJECT-TYPE
  SYNTAX       Integer32 (0..255)
  UNITS        "parts per billion"
  MAX-ACCESS   read-only
  STATUS       current
  DESCRIPTION
    "<Definition> The concentration of nitric oxide in the air, measured in parts per billion.
    <Format>
The value 255 shall indicate an error condition or missing value. 
    <Parameter Type> status
    <Object Identifier> 1.3.6.1.4.1.1206.4.2.5.2.12.14"
::= { essNtcipAirQuality 14 }

-- 5.14.15 Ozone Version 4 Parameter
essO3V4 OBJECT-TYPE
  SYNTAX       Integer32 (0..65535)
  UNITS        "parts per billion"
  MAX-ACCESS   read-only
  STATUS       current
  DESCRIPTION
    "<Definition> The concentration of ozone in the air, measured in parts per billion.
    <Format>
The value 65535 shall indicate an error condition or missing value.
    <Parameter Type> status
    <Object Identifier> 1.3.6.1.4.1.1206.4.2.5.2.12.15"
::= { essNtcipAirQuality 15 }

-- 5.14.16 Particulate Matter (1.0) Parameter
essPM1 OBJECT-TYPE
  SYNTAX       Integer32 (0..65535)
  UNITS        "micrograms per cubic meter"
  MAX-ACCESS   read-only
  STATUS       current
  DESCRIPTION
    "<Definition> The concentration of small particulate matter of 1.0 micrometers or less in diameter in the air, measured in micrograms per cubic meter.
    <Format>
The value 65535 shall indicate an error condition or missing value.
    <Parameter Type> status
    <Object Identifier> 1.3.6.1.4.1.1206.4.2.5.2.12.16"
::= { essNtcipAirQuality 16 }

-- 5.15 Water Quality Parameters
essNtcipWaterQuality OBJECT-IDENTITY
    STATUS       current
  DESCRIPTION
    "<Definition> This node contains objects used for monitoring water quality conditions. Reserved for future use.
    <Object Identifier> 1.3.6.1.4.1.1206.4.2.5.2.13"
::= { essNtcip 13 }

-- 5.16 Snapshot Parameters
essNtcipSnapshot OBJECT-IDENTITY
    STATUS       current
  DESCRIPTION
    "<Definition> Contains objects used to describe the snapshot camera feature.
    <Object Identifier> 1.3.6.1.4.1.1206.4.2.5.2.14"
::= { essNtcip 14 }

-- 5.16.1 Number of Snapshot Cameras
essSnapshotNumberOfCameras OBJECT-TYPE
  SYNTAX       Integer32 (0..255)
  MAX-ACCESS   read-only
  STATUS       current
  DESCRIPTION
    "<Definition> Indicates the number of cameras that can be utilized for capturing snapshots on the ESS.
    <Parameter Type> status
    <Informative> This value may automatically change upon connecting or disconnecting a camera; however, the table is still defined as a static table since the creation/deletion of rows is not managed through SNMP logic.
    <Object Identifier> 1.3.6.1.4.1.1206.4.2.5.2.14.1"
::= { essNtcipSnapshot 1 }

-- 5.16.2 Snapshot Camera Table
essSnapshotCameraTable OBJECT-TYPE
  SYNTAX       SEQUENCE OF EssSnapshotCameraEntry
  MAX-ACCESS   not-accessible
  STATUS       current
  DESCRIPTION
    "<Definition> The snapshot camera table provides summary information about the snapshot cameras supported by the ESS. It can be described through a number of attributes as indicated by the following subclauses.
    <Object Identifier> 1.3.6.1.4.1.1206.4.2.5.2.14.2"
::= { essNtcipSnapshot 2 }

-- 5.16.3 Snapshot Camera
essSnapshotCameraEntry OBJECT-TYPE
  SYNTAX       EssSnapshotCameraEntry
  MAX-ACCESS   not-accessible
  STATUS       current
  DESCRIPTION
    "<Definition> A snapshot camera is a camera that is able to capture a picture and store it within the device's memory as a file. It can be described through a number of attributes as indicated by the following subclauses."
  INDEX { essSnapshotCameraIndex }
::= { essSnapshotCameraTable 1 }

EssSnapshotCameraEntry ::= SEQUENCE {
    essSnapshotCameraIndex            Integer32,
    essSnapshotCameraDescription      SnmpAdminString,
    essSnapshotCameraStoragePath      SnmpAdminString,
    essSnapshotCameraCommand          INTEGER,
    essSnapshotCameraError            INTEGER,
    essSnapshotCameraFilename         OCTET STRING,
    essSnapshotCameraSupportedFormats BITS,
    essSnapshotCameraFileFormat       DisplayString,
    essSnapshotCameraFilenameV5       SnmpAdminString,
    essSnapshotCameraEntityID         PhysicalIndexOrZero }

-- 5.16.3.1 Snapshot Camera Index
essSnapshotCameraIndex OBJECT-TYPE
  SYNTAX       Integer32 (1..255)
  MAX-ACCESS   read-only
  STATUS       current
  DESCRIPTION
    "<Definition> Indicates the row number of this entry.
    <Parameter Type> status
    <Object Identifier> 1.3.6.1.4.1.1206.4.2.5.2.14.2.1.1"
::= { essSnapshotCameraEntry 1 }

-- 5.16.3.2 Snapshot Camera Description
essSnapshotCameraDescription OBJECT-TYPE
  SYNTAX       SnmpAdminString
  MAX-ACCESS   read-write
  STATUS       current
  DESCRIPTION
    "<Definition> Indicates the description of this entry. The description should include information about the location, direction (for fixed cameras), and subject of the camera.
    <Parameter Type> configuration
    <Object Identifier> 1.3.6.1.4.1.1206.4.2.5.2.14.2.1.2"
::= { essSnapshotCameraEntry 2 }

-- 5.16.3.3 Snapshot Camera Storage Path
essSnapshotCameraStoragePath OBJECT-TYPE
  SYNTAX       SnmpAdminString (SIZE(1..255))
  MAX-ACCESS   read-only
  STATUS       current
  DESCRIPTION
    "<Definition> Indicates the storage path of snapshots taken from this camera. The path indicated here shall be relative to the FTP login root. This path can only include the FTP login root and its subdirectories and cannot include any parent directories that may exist. The root is specified by the string '/' (one forward slash). A subdirectory from the root may be specified by the string '/subdir'.
    <Parameter Type> status
    <Object Identifier> 1.3.6.1.4.1.1206.4.2.5.2.14.2.1.3"
  DEFVAL { "/" }
::= { essSnapshotCameraEntry 3 }

-- 5.16.3.4 Snapshot Camera Command
essSnapshotCameraCommand OBJECT-TYPE
  SYNTAX       INTEGER {
    ready(1),
    captureSnapshot(2)  }
  MAX-ACCESS   read-write
  STATUS       current
  DESCRIPTION
    "<Definition> A command to control the snapshot feature of the ESS. Setting this object to a value of captureSnapshot(2) commands the ESS to take a snapshot and save the image to memory. A Get of this object returns a value of captureSnapshot(2) while the ESS is in the process of capturing and saving the image to memory. A Get of this object when the ESS is not in the process of capturing and saving the image to memory returns a value of ready(1). If any errors occur in the process of capturing and saving the image they shall be noted in essSnapshotError.
    <Parameter Type> control
    <Informative> Version 02 of this standard had a typo for the MAX-ACCESS; this object is required tobe read-write for the camera to capture a snapshot image.
    <Object Identifier> 1.3.6.1.4.1.1206.4.2.5.2.14.2.1.4"
::= { essSnapshotCameraEntry 4 }

-- 5.16.3.5 Snapshot Camera Error
essSnapshotCameraError OBJECT-TYPE
  SYNTAX       INTEGER {
    none(1),
    hardware(2),
    insufficientMemory(3)  }
  MAX-ACCESS   read-only
  STATUS       current
  DESCRIPTION
    "<Definition> Indicates the status of the last attempt to capture a snapshot using essSnapshotCommand.
    <Format>
none - no error was detected 
hardware - an error occurred with the camera hardware when attempting to 
    capture a picture.
insufficientMemory - the ESS does not have sufficient memory to store the new 
    picture.
    <Parameter Type> status
    <Object Identifier> 1.3.6.1.4.1.1206.4.2.5.2.14.2.1.5"
::= { essSnapshotCameraEntry 5 }

-- 5.16.3.6 Snapshot Camera Filename
-- This object has been deprecated.
essSnapshotCameraFilename OBJECT-TYPE
  SYNTAX       OCTET STRING (SIZE(0..255))
  MAX-ACCESS   read-write
  STATUS       deprecated
  DESCRIPTION
    "<Definition> Indicates the filename used when storing new snapshot images. 
    <Format>
This parameter shall only consist of upper and lower case characters (A-Z, 
a-z), digits (0-9), underscores (_), periods (.), spaces, and the following
case-sensitive field names enclosed in chevrons (<>):
camera: A three digit camera number equal to essSnapshotCameraIndex.
sequence: A three digit value that increments by one each time this 
camera is used to take a picture. This value shall roll-over from '999' to 
    '000'. The initial value of this field and its value after a power outage 
    is manufacture dependent.
date: A six digit code indicating the UTC date in the format of YYMMDD.
time: A six digit code indicating the UTC time in the format of HHMMSS.


All implementations shall support all static character filenames with up to 
eight characters in the base filename, a period, and up to three characters 
in the filename extension. Support for longer filenames and the above fields 
are optional.


For example, if this parameter has a value of 'latest.jpg', every snapshot 
taken is saved to 'latest.jpg' and overwrites any previous image saved to 
that filename. If this parameter has a value of '<date> <sequence>.jpg', each 
snapshot has a name (e.g., '060925 038') indicating the date it was taken 
along with a relatively unique code. While the second form prevents the 
inadvertent overwriting of filenames, it increases the likelihood of 
consuming large amounts of field device memory (eventually resulting in 
insufficientMemory errors) if not properly managed by the management station.
    <Parameter Type> configuration
    <Superseded by> essSnapshotCameraFilenameV5 and essSnapshotCameraFileFormat
    <Informative> This object was deprecated in version 05. 
The filename does not necessarily define file format and it is left to the users to define an appropriate filename. For example, this object may be set to a value of 'latest.bmp'. All implementations would be required to save their images with this filename; however, the image saved may vary. Some implementations may only save bitmapped images and the file would have an appropriate name. Other implementations may only save JPEG images and the '.bmp' extension may be confusing. Other implementations may support both formats and use the extension in this field to select the storage format, while yet others may support both formats but ignore the extension assigned by this field (and use some other mechanism to select the storage format).
A zero length filename may result in unexpected operations. An implementation may reject a zero length filename by responding with genErr.
    <Object Identifier> 1.3.6.1.4.1.1206.4.2.5.2.14.2.6"
::= { essSnapshotCameraEntry 6 }

-- 5.16.3.7 Snapshot Camera Supported Formats
essSnapshotCameraSupportedFormats OBJECT-TYPE
  SYNTAX       BITS {
    other (0),
    jpeg (1),
    heif (2),
    tiff (3),
    png (4),
    gif (5),
    bmp (6),
    webp (7),
    pdf (8),
    eps (9),
    raw (10),
    dng (11) }
  MAX-ACCESS   read-only
  STATUS       current
  DESCRIPTION
    "<Definition> Indicates the file formats supported by the camera when storing new snapshot images.
<SetConstraint> Can only be set to 'captureSnapshot' when value is currently 'ready'; any other SET shall return a genErr, including a SET to 'ready'. 
    <Format>
other: A file format not identified by this document. If other file formats 
       are used, they shall be presented in all uppercase to avoid conflicts 
       with future extensions to this list.
jpeg: Joint Photographic Experts Group format as standardized in ISO/IEC 
      10918.
heif: High Efficiency Image File format as standardized in ISO/IEC 23008-12.
tiff: Tagged Image File Format, Revision 6.0 as defined by the Aldus 
      Corporation and available from ITU at https://www.itu.int/itudoc/itu-
      t/com16/tiff-fx/docs/tiff6.pdf
png:  Portable Network Graphics (Third Edition) as defined by the World Wide 
      Web Consortium (W3C) and available at https://www.w3.org/TR/png-3/.
gif:  Graphics Interchange Format Version 89a as developed by CompuServe
      Incorporated and available at https://www.w3.org/Graphics/GIF/spec-
      gif89a.txt
bmp:  Microsoft Windows Bitmap Format, version 5 as defined by Microsoft 
      Corporation and available at https://learn.microsoft.com/en-
      us/windows/win32/gdi/bitmap-storage
webp: The raster graphics file format developed by Google and available at 
      https://developers.google.com/speed/webp/docs/riff_container
pdf:  Portable Document Format as developed by Adobe, Inc. and standardized 
      in ISO 32000-2.
eps:  Encapsulated PostScript File Format, Version 3 as specified by Adobe
      Systems Incorporated in May 1992 and available at 
      https://printtechnologies.org/standards/files/epsf_spec_v3_0.pdf
raw:  The native format offered by the camera manufacturer. This format is 
      not interoperable among manufacturers or perhaps even models, but 
      ensures no loss of information.
dng:  Digital Negative, Version 1.7.1.0 format as developed by Adobe as a 
      generic, interoperable raw format and available at https://
      helpx.adobe.com/content/dam/help/en/photoshop/pdf/DNG_Spec_1_7_1_0.pdf
    <Parameter Type> status
    <Object Identifier> 1.3.6.1.4.1.1206.4.2.5.2.14.2.7"
::= { essSnapshotCameraEntry 7 }

-- 5.16.3.8 Snapshot Camera File Format
essSnapshotCameraFileFormat OBJECT-TYPE
  SYNTAX       DisplayString(SIZE (1..8))
  MAX-ACCESS   read-write
  STATUS       current
  DESCRIPTION
    "<Definition> Indicates the filename extension to use when storing new snapshot images. If this parameter equals the name of a named bit defined by essSnapshotCameraSupportedFormats, the format shall be stored in the indicated file format. Other file formats can be used but shall use all uppercase characters to prevent conflicts with future standardized assignments. 
The ESS shall respond with a wrongValue error for an attempt to set this object to a file format value that the camera does not support 
    <Parameter Type> configuration
    <Object Identifier> 1.3.6.1.4.1.1206.4.2.5.2.14.2.8"
::= { essSnapshotCameraEntry 8 }

-- 5.16.3.9 Snapshot Camera Filename Version 5
essSnapshotCameraFilenameV5 OBJECT-TYPE
  SYNTAX       SnmpAdminString (SIZE (1..255))
  MAX-ACCESS   read-write
  STATUS       current
  DESCRIPTION
    "<Definition> Indicates the filename used when storing new snapshot images.
    <Format>
Case-sensitive field names enclosed in chevrons (<>) shall be interpreted as 
follows:


camera: A three digit camera number equal to essSnapshotCameraIndex.
sequence: A three digit value that increments by one each time this 
camera is used to take a picture. This value shall roll-over from '999' to 
    '000'. The initial value of this field and its value after a power outage 
    is manufacture dependent.
date: A six digit code indicating the UTC date in the format of YYMMDD.
time: A six digit code indicating the UTC time in the format of HHMMSS.


All implementations shall support all static NVT-ASCII character filenames 
with up to eight characters in the base filename. Support for longer 
filenames, the above fields, and non-NVT-ASCII characters are optional.


For example, if this parameter has a value of 'latest' and the value of 
essSnapshotCameraFileFormat is 'jpeg', every snapshot taken is saved to 
'latest.jpeg' and overwrites any previous image saved to that filename. If 
this parameter has a value of '<date> <sequence>', each snapshot has a base 
name (e.g., '060925 038') indicating the date it was taken along with a 
relatively unique code. While the second form prevents the inadvertent 
overwriting of filenames, it increases the likelihood of consuming large 
amounts of field device memory (eventually resulting in insufficientMemory 
errors) if not properly managed by the management station.
    <Parameter Type> configuration
    <Object Identifier> 1.3.6.1.4.1.1206.4.2.5.2.14.2.9"
::= { essSnapshotCameraEntry 9 }

-- 5.16.3.10 Snapshot Camera Entity ID
essSnapshotCameraEntityID OBJECT-TYPE
  SYNTAX       PhysicalIndexOrZero
  MAX-ACCESS   read-only
  STATUS       current
  DESCRIPTION
    "<Definition> Indicates the row in the entPhysicalTable (See RFC 4133) that contains information about the sensor, such as the manufacturer, model, and hardware and software revision identifiers.
    <Format>
The value of zero indicates that this information is not available.
    <Parameter Type> status
    <Informative> The mechanism used to configure this value when adding or modifying a camera is not defined by this document and is considered manufacturer-specific.
    <Object Identifier> 1.3.6.1.4.1.1206.4.2.5.2.14.2.10"
::= { essSnapshotCameraEntry 10 }

-- 5.17 Conformance Information
essConformance OBJECT-IDENTITY
    STATUS       current
  DESCRIPTION
    "<Definition> A node defining conformance information related to ESS objects.
    <Object Identifier> 1.3.6.1.4.1.1206.4.2.5.127"
::= {ess 127}

essCompliances OBJECT-IDENTITY
    STATUS       current
  DESCRIPTION
    "<Definition> A node for compliance statements for ESS objects.
    <Object Identifier> 1.3.6.1.4.1.1206.4.2.5.127.1"
::= {essConformance 1}

essGroups OBJECT-IDENTITY
    STATUS       current
  DESCRIPTION
    "<Definition> A node for group definitions related to ESS objects.
    <Object Identifier> 1.3.6.1.4.1.1206.4.2.5.127.2"
::= {essConformance 2}

-- 5.17.1 Controller Groups
essControllerGroups OBJECT-IDENTITY
    STATUS       current
  DESCRIPTION
    "<Definition> A node for group definitions related to ESS objects.
    <Object Identifier> 1.3.6.1.4.1.1206.4.2.5.127.2.1"
::= {essGroups 1}

-- This object has been deprecated.
essCharacteristicsGroupV1 OBJECT-GROUP
  OBJECTS {
      essNtcipCategory,
      essNtcipSiteDescription,
      essTypeofStation,
      essLatitude,
      essLongitude,
      essReferenceHeight }
  STATUS   deprecated
  DESCRIPTION
    "<Definition> The NTCIP 1204 objects required to claim base conformance to NTCIP 1204 v01.
    <Superseded by> essCharacteristicsGroupV5
    <Object Identifier> 1.3.6.1.4.1.1206.4.2.5.127.2.1.1"
::= {essControllerGroups 1}

-- This object has been deprecated.
essMobileGroupV1 OBJECT-GROUP
  OBJECTS {
      essVehicleSpeed,
      essVehicleBearing,
      essOdometer }
  STATUS   deprecated
  DESCRIPTION
    "<Definition> The objects required to claim support for a mobile ESS in v01.
    <Superseded by> ISO26048-1-FieldDevice.fdMobilityGroupV1
    <Object Identifier> 1.3.6.1.4.1.1206.4.2.5.127.2.1.2"
::= {essControllerGroups 2}

-- This object has been deprecated.
essMobileFrictionGroupV1 OBJECT-GROUP
  OBJECTS {
      essMobileFriction }
  STATUS   deprecated
  DESCRIPTION
    "<Definition> The objects required to claim support for mobile mobile friction in v01.
    <Superseded by> essPavementFrictionGroupV4
    <Object Identifier> 1.3.6.1.4.1.1206.4.2.5.127.2.1.3"
::= {essControllerGroups 3}

-- This object has been deprecated.
essDoorStatusGroupV2 OBJECT-GROUP
  OBJECTS {
      essDoorStatus }
  STATUS   deprecated
  DESCRIPTION
    "<Definition> The NTCIP 1204 objects required to claim conformance to door status in v02.
    <Superseded by> ISO26048-1-Srsa.fdSrsaBasicGroupV1, where fdSrsaTypeCode = FBO
    <Object Identifier> 1.3.6.1.4.1.1206.4.2.5.127.2.1.4"
::= {essControllerGroups 4}

-- This object has been deprecated.
essBatteryGroupV2 OBJECT-GROUP
  OBJECTS {
      essBatteryStatus }
  STATUS   deprecated
  DESCRIPTION
    "<Definition> The NTCIP 1204 objects required to claim base conformance to battery status in v02.
    <Superseded by> ISO26048-1-Srsa.fdSrsaInputGroupV1, where fdSrsaTypeCode = FBC
    <Object Identifier> 1.3.6.1.4.1.1206.4.2.5.127.2.1.5"
::= {essControllerGroups 5}

-- This object has been deprecated.
essLineVoltsGroupV2 OBJECT-GROUP
  OBJECTS {
      essLineVolts }
  STATUS   deprecated
  DESCRIPTION
    "<Definition> The NTCIP 1204 objects required to claim base conformance to line volts in v02.
    <Superseded by> ISO26048-1-Srsa.fdSrsaInputGroupV1, where fdSrsaTypeCode = FLV
    <Object Identifier> 1.3.6.1.4.1.1206.4.2.5.127.2.1.6"
::= {essControllerGroups 6}

-- This object has been deprecated.
essMetaDataBlockGroupV2 OBJECT-GROUP
  OBJECTS {
      essStationMetaDataBlock }
  STATUS   deprecated
  DESCRIPTION
    "<Definition> The objects required to claim support for the metadata block in v02.
    <Superseded by> essMetaDataBlockGroupV3
    <Object Identifier> 1.3.6.1.4.1.1206.4.2.5.127.2.1.7"
::= {essControllerGroups 7}

-- This object has been deprecated.
essMobileBlockGroupV2 OBJECT-GROUP
  OBJECTS {
      essMobileBlock }
  STATUS   deprecated
  DESCRIPTION
    "<Definition> The objects required to claim support for the mobile block in v02.
    <Withdrawn> In v04
    <Object Identifier> 1.3.6.1.4.1.1206.4.2.5.127.2.1.8"
::= {essControllerGroups 8}

-- This object has been deprecated.
essWeatherBlockGroupV2 OBJECT-GROUP
  OBJECTS {
      essWeatherBlock }
  STATUS   deprecated
  DESCRIPTION
    "<Definition> The objects required to claim support for the weather block in v02.
    <Superseded by> essWeatherBlockGroupV3
    <Object Identifier> 1.3.6.1.4.1.1206.4.2.5.127.2.1.9"
::= {essControllerGroups 9}

-- This object has been deprecated.
essMetaDataBlockGroupV3 OBJECT-GROUP
  OBJECTS {
      essStationMetaDataV3Block }
  STATUS   deprecated
  DESCRIPTION
    "<Definition> The objects required to claim support for the metadata block in v03.
    <Withdrawn> In v04
    <Object Identifier> 1.3.6.1.4.1.1206.4.2.5.127.2.1.10"
::= {essControllerGroups 10}

-- This object has been deprecated.
essWeatherBlockGroupV3 OBJECT-GROUP
  OBJECTS {
      essWeatherV3Block }
  STATUS   deprecated
  DESCRIPTION
    "<Definition> The objects required to claim support for the weather block in v03.
    <Withdrawn> In v04
    <Object Identifier> 1.3.6.1.4.1.1206.4.2.5.127.2.1.11"
::= {essControllerGroups 11}

-- This object has been deprecated.
essStatusGroupV3 OBJECT-GROUP
  OBJECTS {
      essStatus }
  STATUS   deprecated
  DESCRIPTION
    "<Definition> The objects required to claim support for monitoring ESS status in v04.
    <Superseded by> ISO26048-1-Controller.fdControllerGroupV1
    <Object Identifier> 1.3.6.1.4.1.1206.4.2.5.127.2.1.12"
::= {essControllerGroups 12}

essCharacteristicsGroupV5 OBJECT-GROUP
  OBJECTS {
      essTypeofStation }
  STATUS   current
  DESCRIPTION
    "<Definition> The NTCIP 1204 objects required to claim base conformance to NTCIP 1204 v05. 
    <Object Identifier> 1.3.6.1.4.1.1206.4.2.5.127.2.13"
::= {essControllerGroups 13}

-- 5.17.2 Pressure Groups
essPressureGroups OBJECT-IDENTITY
    STATUS       current
  DESCRIPTION
    "<Definition> A node for group definitions related to ESS pressure sensor objects.
    <Object Identifier> 1.3.6.1.4.1.1206.4.2.5.127.2.2"
::= {essGroups 2}

-- This object has been deprecated.
essPressureGroupV1 OBJECT-GROUP
  OBJECTS {
      essPressureHeight,
      essAtmosphericPressure }
  STATUS   deprecated
  DESCRIPTION
    "<Definition> The objects required to claim support for atmospheric pressure readings for v01.
    <Superseded by> essPressureSensorLocationGroupV4 and essPressureDataGroupV4
    <Object Identifier> 1.3.6.1.4.1.1206.4.2.5.127.2.2.1"
::= {essPressureGroups 1}

-- This object has been deprecated.
essPressureSensorLocationGroupV4 OBJECT-GROUP
  OBJECTS {
      essPressureSensorHeight,
      essPressureSensorLatitude,
      essPressureSensorLongitude,
      essPressureSensorLocation }
  STATUS   deprecated
  DESCRIPTION
    "<Definition> The objects required to claim support for atmospheric pressure readings for v04.
    <Superseded by> essPressureSensorLocationGroupV5
    <Object Identifier> 1.3.6.1.4.1.1206.4.2.5.127.2.2.2"
::= {essPressureGroups 2}

-- This object has been deprecated.
essPressureSensorInfoGroupV4 OBJECT-GROUP
  OBJECTS {
      essPressureSensorModelInformation }
  STATUS   deprecated
  DESCRIPTION
    "<Definition> The objects required to claim support for pressure sensor identification for v04.
    <Superseded by> essPressureSensorInfoGroupV5
    <Object Identifier> 1.3.6.1.4.1.1206.4.2.5.127.2.2.3"
::= {essPressureGroups 3}

essPressureDataGroupV4 OBJECT-GROUP
  OBJECTS {
      essNumPressureSensors,
      essPressureSensorIndex,
      essPressureSensorAtmosphericPressure }
  STATUS   current
  DESCRIPTION
    "<Definition> The objects required to claim support for atmospheric pressure readings for v04. 
    <Object Identifier> 1.3.6.1.4.1.1206.4.2.5.127.2.2.4"
::= {essPressureGroups 4}

essPressureSensorLocationGroupV5 OBJECT-GROUP
  OBJECTS {
      essPressureSensorLocation,
      essPressureSensorXOffset,
      essPressureSensorYOffset,
      essPressureSensorZOffset }
  STATUS   current
  DESCRIPTION
    "<Definition> The objects required to claim support for pressure sensor location for v05. 
    <Object Identifier> 1.3.6.1.4.1.1206.4.2.5.127.2.2.5"
::= {essPressureGroups 5}

essPressureSensorInfoGroupV5 OBJECT-GROUP
  OBJECTS {
      essPressureSensorEntityID }
  STATUS   current
  DESCRIPTION
    "<Definition> The objects required to claim support for pressure sensor identification for v05. 
    <Object Identifier> 1.3.6.1.4.1.1206.4.2.5.127.2.2.6"
::= {essPressureGroups 6}

-- 5.17.3 Wind Groups
essWindGroups OBJECT-IDENTITY
    STATUS       current
  DESCRIPTION
    "<Definition> A node for group definitions related to ESS wind sensor objects.
    <Object Identifier> 1.3.6.1.4.1.1206.4.2.5.127.2.3"
::= {essGroups 3}

-- This object has been deprecated.
essWindGroupV1 OBJECT-GROUP
  OBJECTS {
      essWindSensorHeight,
      essAvgWindDirection,
      essAvgWindSpeed,
      essMaxWindGustSpeed,
      essMaxWindGustDir }
  STATUS   deprecated
  DESCRIPTION
    "<Definition> The objects required to claim support for wind data in v01.
    <Superseded by> essWindDataGroupV2 and essWindSensorLocationGroupV2
    <Object Identifier> 1.3.6.1.4.1.1206.4.2.5.127.2.3.1"
::= {essWindGroups 1}

-- This object has been deprecated.
essMobileWindGroupV1 OBJECT-GROUP
  OBJECTS {
      essSpotWindDirection,
      essSpotWindSpeed,
      essWindSituation }
  STATUS   deprecated
  DESCRIPTION
    "<Definition> The objects required to claim support for mobile wind data in v01.
    <Superseded by> essWindDataGroupV2
    <Object Identifier> 1.3.6.1.4.1.1206.4.2.5.127.2.3.2"
::= {essWindGroups 2}

essWindDataGroupV2 OBJECT-GROUP
  OBJECTS {
      windSensorTableNumSensors,
      windSensorIndex,
      windSensorAvgSpeed,
      windSensorAvgDirection,
      windSensorSpotSpeed,
      windSensorSpotDirection,
      windSensorGustSpeed,
      windSensorGustDirection,
      windSensorSituation }
  STATUS   current
  DESCRIPTION
    "<Definition> The objects required to claim support for wind data in v02.
    <Object Identifier> 1.3.6.1.4.1.1206.4.2.5.127.2.3.3"
::= {essWindGroups 3}

-- This object has been deprecated.
essWindSensorLocationGroupV2 OBJECT-GROUP
  OBJECTS {
      windSensorHeight,
      windSensorLocation }
  STATUS   deprecated
  DESCRIPTION
    "<Definition> The objects required to claim support for wind sensor location for v02.
    <Superseded by> essWindSensorLocationGroupV5
    <Object Identifier> 1.3.6.1.4.1.1206.4.2.5.127.2.3.4"
::= {essWindGroups 4}

-- This object has been deprecated.
essWindSensorLocationGroupV4 OBJECT-GROUP
  OBJECTS {
      windSensorLatitude,
      windSensorLongitude }
  STATUS   deprecated
  DESCRIPTION
    "<Definition> The objects required to claim support for wind sensor location for v04.
    <Superseded by> essWindSensorLocationGroupV5
    <Object Identifier> 1.3.6.1.4.1.1206.4.2.5.127.2.3.5"
::= {essWindGroups 5}

-- This object has been deprecated.
essWindSensorInfoGroupV4 OBJECT-GROUP
  OBJECTS {
      windSensorModelInformation }
  STATUS   deprecated
  DESCRIPTION
    "<Definition> The objects required to claim support for wind sensor model information for v04.
    <Superseded by> essWindSensorInfoGroupV5
    <Object Identifier> 1.3.6.1.4.1.1206.4.2.5.127.2.3.6"
::= {essWindGroups 6}

essWindSensorLocationGroupV5 OBJECT-GROUP
  OBJECTS {
      windSensorLocation,
      windSensorXOffset,
      windSensorYOffset,
      windSensorZOffset }
  STATUS   current
  DESCRIPTION
    "<Definition> The objects required to claim support for wind sensor location for v05.
    <Object Identifier> 1.3.6.1.4.1.1206.4.2.5.127.2.3.7"
::= {essWindGroups 7}

essWindSensorInfoGroupV5 OBJECT-GROUP
  OBJECTS {
      windSensorEntityID }
  STATUS   current
  DESCRIPTION
    "<Definition> The objects required to claim support for wind sensor identification for v05.
    <Object Identifier> 1.3.6.1.4.1.1206.4.2.5.127.2.3.8"
::= {essWindGroups 8}

-- 5.17.4 Temperature Groups
essTemperatureGroups OBJECT-IDENTITY
    STATUS       current
  DESCRIPTION
    "<Definition> A node for group definitions related to ESS temperture sensor objects.
    <Object Identifier> 1.3.6.1.4.1.1206.4.2.5.127.2.4"
::= {essGroups 4}

essTemperatureGroupV1 OBJECT-GROUP
  OBJECTS {
      essNumTemperatureSensors,
      essTemperatureSensorIndex,
      essAirTemperature,
      essMaxTemp,
      essMinTemp }
  STATUS   current
  DESCRIPTION
    "<Definition> The objects required to claim support for temperature readings for v01.
    <Object Identifier> 1.3.6.1.4.1.1206.4.2.5.127.2.4.1"
::= {essTemperatureGroups 1}

-- This object has been deprecated.
essTemperatureSensorLocationGroupV1 OBJECT-GROUP
  OBJECTS {
      essTemperatureSensorHeight }
  STATUS   deprecated
  DESCRIPTION
    "<Definition> The objects required to claim support for temperature sensor location for v01.
    <Superseded by> essTemperatureSensorLocationGroupV5
    <Object Identifier> 1.3.6.1.4.1.1206.4.2.5.127.2.4.2"
::= {essTemperatureGroups 2}

-- This object has been deprecated.
essTemperatureSensorLocationGroupV4 OBJECT-GROUP
  OBJECTS {
      essTemperatureSensorLatitude,
      essTemperatureSensorLongitude,
      essTemperatureSensorLocation }
  STATUS   deprecated
  DESCRIPTION
    "<Definition> The objects required to claim support for temperature sensor location for v04.
    <Superseded by> essTemperatureSensorLocationGroupV5
    <Object Identifier> 1.3.6.1.4.1.1206.4.2.5.127.2.4.3"
::= {essTemperatureGroups 3}

-- This object has been deprecated.
essTemperatureSensorInfoGroupV4 OBJECT-GROUP
  OBJECTS {
      essTemperatureSensorModelInformation }
  STATUS   deprecated
  DESCRIPTION
    "<Definition> The objects required to claim support for temperature sensor model information for v04.
    <Superseded by> essTemperatureSensorInfoGroupV5
    <Object Identifier> 1.3.6.1.4.1.1206.4.2.5.127.2.4.4"
::= {essTemperatureGroups 4}

essTemperatureSensorLocationGroupV5 OBJECT-GROUP
  OBJECTS {
      essTemperatureSensorLocation,
      essTemperatureSensorXOffset,
      essTemperatureSensorYOffset,
      essTemperatureSensorZOffset }
  STATUS   current
  DESCRIPTION
    "<Definition> The objects required to claim support for temperature sensor location for v05.
    <Object Identifier> 1.3.6.1.4.1.1206.4.2.5.127.2.4.5"
::= {essTemperatureGroups 5}

essTemperatureSensorInfoGroupV5 OBJECT-GROUP
  OBJECTS {
      essTemperatureSensorEntityID }
  STATUS   current
  DESCRIPTION
    "<Definition> The objects required to claim support for temperature sensor identification for v05.
    <Object Identifier> 1.3.6.1.4.1.1206.4.2.5.127.2.4.6"
::= {essTemperatureGroups 6}

-- 5.17.5 Humidity Groups
essHumidityGroups OBJECT-IDENTITY
    STATUS       current
  DESCRIPTION
    "<Definition> A node for group definitions related to ESS humidity objects.
    <Object Identifier> 1.3.6.1.4.1.1206.4.2.5.127.2.5"
::= {essGroups 5}

-- This object has been deprecated.
essHumidityGroupV1 OBJECT-GROUP
  OBJECTS {
      essWetbulbTemp,
      essDewpointTemp,
      essRelativeHumidity }
  STATUS   deprecated
  DESCRIPTION
    "<Definition> The objects required to claim support for humidity readings for v01.
    <Superseded by> essHumidityDataGroupV5
    <Object Identifier> 1.3.6.1.4.1.1206.4.2.5.127.2.5.1"
::= {essHumidityGroups 1}

-- This object has been deprecated.
essHumiditySensorLocationGroupV4 OBJECT-GROUP
  OBJECTS {
      humiditySensorHeight,
      humiditySensorLatitude,
      humiditySensorLongitude,
      humiditySensorLocation }
  STATUS   deprecated
  DESCRIPTION
    "<Definition> The objects required to claim support for humidity sensor location for v04.
    <Superseded by> essHumiditySensorLocationGroupV5
    <Object Identifier> 1.3.6.1.4.1.1206.4.2.5.127.2.5.2"
::= {essHumidityGroups 2}

-- This object has been deprecated.
essHumiditySensorInfoGroupV4 OBJECT-GROUP
  OBJECTS {
      humiditySensorModelInformation }
  STATUS   deprecated
  DESCRIPTION
    "<Definition> The objects required to claim support for humidity sensor identification for v04.
    <Superseded by> essHumiditySensorInfoGroupV5
    <Object Identifier> 1.3.6.1.4.1.1206.4.2.5.127.2.5.3"
::= {essHumidityGroups 3}

essHumidityDataGroupV4 OBJECT-GROUP
  OBJECTS {
      humiditySensorTableNumSensors,
      humiditySensorIndex,
      humiditySensorRelativeHumidity,
      humiditySensorTemperatureInformation,
      humiditySensorWetbulbTemp,
      humiditySensorDewpointTemp }
  STATUS   current
  DESCRIPTION
    "<Definition> The objects required to claim support for humidity readings for v04. 
    <Object Identifier> 1.3.6.1.4.1.1206.4.2.5.127.2.5.4"
::= {essHumidityGroups 4}

essHumiditySensorLocationGroupV5 OBJECT-GROUP
  OBJECTS {
      humiditySensorLocation,
      humiditySensorXOffset,
      humiditySensorYOffset,
      humiditySensorZOffset }
  STATUS   current
  DESCRIPTION
    "<Definition> The objects required to claim support for humidity sensor location for v05.
    <Object Identifier> 1.3.6.1.4.1.1206.4.2.5.127.2.5.5"
::= {essHumidityGroups 5}

essHumiditySensorInfoGroupV5 OBJECT-GROUP
  OBJECTS {
      humiditySensorEntityID }
  STATUS   current
  DESCRIPTION
    "<Definition> The objects required to claim support for humidity sensor identification for v05.
    <Object Identifier> 1.3.6.1.4.1.1206.4.2.5.127.2.5.6"
::= {essHumidityGroups 6}

-- 5.17.6 Precipitation Groups
essPrecipitationGroups OBJECT-IDENTITY
    STATUS       current
  DESCRIPTION
    "<Definition> A node for group definitions related to ESS precipitation objects.
    <Object Identifier> 1.3.6.1.4.1.1206.4.2.5.127.2.6"
::= {essGroups 6}

-- This object has been deprecated.
essPrecipPresenceGroupV1 OBJECT-GROUP
  OBJECTS {
      essPrecipYesNo }
  STATUS   deprecated
  DESCRIPTION
    "<Definition> The objects required to claim support for precipitation presence for v01.
    <Superseded by> essPrecipPresenceGroupV4
    <Object Identifier> 1.3.6.1.4.1.1206.4.2.5.127.2.6.1"
::= {essPrecipitationGroups 1}

-- This object has been deprecated.
essPrecipRateGroupV1 OBJECT-GROUP
  OBJECTS {
      essPrecipRate,
      essPrecipitationStartTime,
      essPrecipitationEndTime }
  STATUS   deprecated
  DESCRIPTION
    "<Definition> The objects required to claim support for precipitation rate for v01.
    <Superseded by> essPrecipDataGroupV4
    <Object Identifier> 1.3.6.1.4.1.1206.4.2.5.127.2.6.2"
::= {essPrecipitationGroups 2}

-- This object has been deprecated.
essPrecipTotalsGroupV1 OBJECT-GROUP
  OBJECTS {
      essPrecipSituation,
      essPrecipitationOneHour,
      essPrecipitationThreeHours,
      essPrecipitationSixHours,
      essPrecipitationTwelveHours,
      essPrecipitation24Hours }
  STATUS   deprecated
  DESCRIPTION
    "<Definition> The objects required to claim support for precipitation totals for v01.
    <Superseded by> essPrecipTotalsGroupV4 and essPrecipSituationGroupV4
    <Object Identifier> 1.3.6.1.4.1.1206.4.2.5.127.2.6.3"
::= {essPrecipitationGroups 3}

-- This object has been deprecated.
essPrecipEmergingGroupV1 OBJECT-GROUP
  OBJECTS {
      essAdjacentSnowDepth,
      essRoadwaySnowDepth,
      essRoadwaySnowPackDepth,
      essSnowfallAccumRate,
      essIceThickness }
  STATUS   deprecated
  DESCRIPTION
    "<Definition> The objects required to claim support for emergent precipitation information for v01.
    <Superseded by> essPrecipDataGroupV4, essPrecipIceThicknessGroupV4, essPrecipAdjacentSnowGroupV4, and essPrecipRoadwaySnowGroupV4
    <Object Identifier> 1.3.6.1.4.1.1206.4.2.5.127.2.6.4"
::= {essPrecipitationGroups 4}

-- This object has been deprecated.
essPrecipSensorInfoGroupV2 OBJECT-GROUP
  OBJECTS {
      precipitationSensorModelInformation }
  STATUS   deprecated
  DESCRIPTION
    "<Definition> The objects required to claim support for precipitation sensor model information for v02.
    <Superseded by> essPrecipSensorInfoGroupV4
    <Object Identifier> 1.3.6.1.4.1.1206.4.2.5.127.2.6.5"
::= {essPrecipitationGroups 5}

essPrecipPresenceGroupV4 OBJECT-GROUP
  OBJECTS {
      precipitationSensorTableNumSensors,
      precipitationSensorIndex,
      precipitationSensorPrecipYesNo }
  STATUS   current
  DESCRIPTION
    "<Definition> The objects required to claim support for precipitation presence for v04.
    <Object Identifier> 1.3.6.1.4.1.1206.4.2.5.127.2.6.6"
::= {essPrecipitationGroups 6}

-- This object has been deprecated.
essPrecipDataGroupV4 OBJECT-GROUP
  OBJECTS {
      precipitationSensorPrecipRate,
      precipitationSensorSnowfallAccumRate,
      precipitationSensorPrecipitationStartTime,
      precipitationSensorPrecipitationEndTime }
  STATUS   deprecated
  DESCRIPTION
    "<Definition> The objects required to claim support for precipitation data readings for v04.
    <Superseded by> essPrecipDataGroupV5
    <Object Identifier> 1.3.6.1.4.1.1206.4.2.5.127.2.6.7"
::= {essPrecipitationGroups 7}

essPrecipSituationGroupV4 OBJECT-GROUP
  OBJECTS {
      precipitationSensorPrecipSituation }
  STATUS   current
  DESCRIPTION
    "<Definition> The objects required to claim support for precipitation situation readings for v04.
    <Object Identifier> 1.3.6.1.4.1.1206.4.2.5.127.2.6.8"
::= {essPrecipitationGroups 8}

-- This object has been deprecated.
essPrecipIceThicknessGroupV4 OBJECT-GROUP
  OBJECTS {
      precipitationSensorIceThickness }
  STATUS   deprecated
  DESCRIPTION
    "<Definition> The objects required to claim support for ice thickness readings for v04.
    <Superseded by> essPavementTemperatureGroupV2
    <Object Identifier> 1.3.6.1.4.1.1206.4.2.5.127.2.6.9"
::= {essPrecipitationGroups 9}

essPrecipTotalsGroupV4 OBJECT-GROUP
  OBJECTS {
      precipitationSensorPrecipitationOneHour,
      precipitationSensorPrecipitationThreeHours,
      precipitationSensorPrecipitationSixHours,
      precipitationSensorPrecipitationTwelveHours,
      precipitationSensorPrecipitation24Hours }
  STATUS   current
  DESCRIPTION
    "<Definition> The objects required to claim support for precipitation totals for v04.
    <Object Identifier> 1.3.6.1.4.1.1206.4.2.5.127.2.6.10"
::= {essPrecipitationGroups 10}

essPrecipUserTotalGroupV4 OBJECT-GROUP
  OBJECTS {
      precipitationSensorPeriod,
      precipitationSensorPrecipitationUserDefined }
  STATUS   current
  DESCRIPTION
    "<Definition> The objects required to claim support for precipitation user-defined totals for v04.
    <Object Identifier> 1.3.6.1.4.1.1206.4.2.5.127.2.6.11"
::= {essPrecipitationGroups 11}

-- This object has been deprecated.
essPrecipSensorLocationGroupV4 OBJECT-GROUP
  OBJECTS {
      precipitationSensorHeight,
      precipitationSensorLatitude,
      precipitationSensorLongitude,
      precipitationSensorLocation }
  STATUS   deprecated
  DESCRIPTION
    "<Definition> The objects required to claim support for precipitation sensor location for v04.
    <Superseded by> essPrecipSensorInfoGroupV4
    <Object Identifier> 1.3.6.1.4.1.1206.4.2.5.127.2.6.12"
::= {essPrecipitationGroups 12}

-- This object has been deprecated.
essPrecipSensorInfoGroupV4 OBJECT-GROUP
  OBJECTS {
      precipitationSensorModelInformationV4 }
  STATUS   deprecated
  DESCRIPTION
    "<Definition> The objects required to claim support for precipitation sensor model information for v04.
    <Superseded by> essPrecipSensorInfoGroupV5
    <Object Identifier> 1.3.6.1.4.1.1206.4.2.5.127.2.6.13"
::= {essPrecipitationGroups 13}

essPrecipDataGroupV5 OBJECT-GROUP
  OBJECTS {
      precipitationSensorPrecipRate,
      precipitationSensorSnowfallAccumRate,
      precipitationSensorPrecipStartTimeV5,
      precipitationSensorPrecipEndTimeV5 }
  STATUS   current
  DESCRIPTION
    "<Definition> The objects required to claim support for precipitation data readings for v05.
    <Object Identifier> 1.3.6.1.4.1.1206.4.2.5.127.2.6.14"
::= {essPrecipitationGroups 14}

essPrecipSensorLocationGroupV5 OBJECT-GROUP
  OBJECTS {
      precipitationSensorLocation,
      precipitationSensorXOffset,
      precipitationSensorYOffset,
      precipitationSensorZOffset }
  STATUS   current
  DESCRIPTION
    "<Definition> The objects required to claim support for precipitation sensor location for v05.
    <Object Identifier> 1.3.6.1.4.1.1206.4.2.5.127.2.6.15"
::= {essPrecipitationGroups 15}

essPrecipSensorInfoGroupV5 OBJECT-GROUP
  OBJECTS {
      precipitationSensorEntityID }
  STATUS   current
  DESCRIPTION
    "<Definition> The objects required to claim support for precipitation sensor identification for v05.
    <Object Identifier> 1.3.6.1.4.1.1206.4.2.5.127.2.6.16"
::= {essPrecipitationGroups 16}

essPrecipAdjacentSnowGroupV5 OBJECT-GROUP
  OBJECTS {
      precipitationSensorAdjacentSnowDepth }
  STATUS   current
  DESCRIPTION
    "<Definition> The objects required to claim support for adjacent snow readings for v05.
    <Object Identifier> 1.3.6.1.4.1.1206.4.2.5.127.2.6.17"
::= {essPrecipitationGroups 17}

essPrecipRoadwaySnowGroupV5 OBJECT-GROUP
  OBJECTS {
      precipitationSensorRoadwaySnowDepth,
      precipitationSensorRoadwaySnowPackDepth }
  STATUS   current
  DESCRIPTION
    "<Definition> The objects required to claim support for roadway snow readings for v05.
    <Object Identifier> 1.3.6.1.4.1.1206.4.2.5.127.2.6.18"
::= {essPrecipitationGroups 18}

-- 5.17.7 Radiation Groups
essRadiationGroups OBJECT-IDENTITY
    STATUS       current
  DESCRIPTION
    "<Definition> A node for group definitions related to ESS radiation objects.
    <Object Identifier> 1.3.6.1.4.1.1206.4.2.5.127.2.7"
::= {essGroups 7}

-- This object has been deprecated.
essRadiationGroupV1 OBJECT-GROUP
  OBJECTS {
      essSolarRadiation,
      essTotalSun }
  STATUS   deprecated
  DESCRIPTION
    "<Definition> The objects required to claim support for radiation readings for v01.
    <Superseded by> essRadiationGroupV2
    <Object Identifier> 1.3.6.1.4.1.1206.4.2.5.127.2.7.1"
::= {essRadiationGroups 1}

-- This object has been deprecated.
essRadiationGroupV2 OBJECT-GROUP
  OBJECTS {
      essTotalSun,
      essInstantaneousTerrestrialRadiation,
      essInstantaneousSolarRadiation,
      essTotalRadiation,
      essTotalRadiationPeriod }
  STATUS   deprecated
  DESCRIPTION
    "<Definition> The objects required to claim support for radiation readings for v02.
    <Superseded by> essRadiationDataGroupV4
    <Object Identifier> 1.3.6.1.4.1.1206.4.2.5.127.2.7.2"
::= {essRadiationGroups 2}

essRadiationDataGroupV4 OBJECT-GROUP
  OBJECTS {
      essTotalRadiationPeriod,
      radiationSensorTableNumSensors,
      radiationSensorIndex,
      essTotalSunV4,
      essInstantaneousTerrestrialRadiationV4,
      essInstantaneousSolarRadiationV4,
      essTotalRadiationV4 }
  STATUS   current
  DESCRIPTION
    "<Definition> The objects required to claim support for radiation readings for v04.
    <Object Identifier> 1.3.6.1.4.1.1206.4.2.5.127.2.7.3"
::= {essRadiationGroups 3}

-- This object has been deprecated.
essRadiationSensorLocationGroupV4 OBJECT-GROUP
  OBJECTS {
      radiationSensorHeight,
      radiationSensorLatitude,
      radiationSensorLongitude,
      radiationSensorLocation }
  STATUS   deprecated
  DESCRIPTION
    "<Definition> The objects required to claim support for radiation sensor location for v04.
    <Superseded by> essRadiationSensorLocationGroupV5
    <Object Identifier> 1.3.6.1.4.1.1206.4.2.5.127.2.7.4"
::= {essRadiationGroups 4}

-- This object has been deprecated.
essRadiationSensorInfoGroupV4 OBJECT-GROUP
  OBJECTS {
      radiationSensorModelInformation }
  STATUS   deprecated
  DESCRIPTION
    "<Definition> The objects required to claim support for radiation sensor identification for v04.
    <Superseded by> essRadiationSensorInfoGroupV5
    <Object Identifier> 1.3.6.1.4.1.1206.4.2.5.127.2.7.5"
::= {essRadiationGroups 5}

essRadiationSensorLocationGroupV5 OBJECT-GROUP
  OBJECTS {
      radiationSensorLocation,
      radiationSensorXOffset,
      radiationSensorYOffset,
      radiationSensorZOffset }
  STATUS   current
  DESCRIPTION
    "<Definition> The objects required to claim support for radiation sensor location for v05.
    <Object Identifier> 1.3.6.1.4.1.1206.4.2.5.127.2.7.6"
::= {essRadiationGroups 6}

essRadiationSensorInfoGroupV5 OBJECT-GROUP
  OBJECTS {
      radiationSensorEntityID }
  STATUS   current
  DESCRIPTION
    "<Definition> The objects required to claim support for radiation sensor identification for v05.
    <Object Identifier> 1.3.6.1.4.1.1206.4.2.5.127.2.7.7"
::= {essRadiationGroups 7}

-- 5.17.8 Visibility Groups
essVisibilityGroups OBJECT-IDENTITY
    STATUS       current
  DESCRIPTION
    "<Definition> A node for group definitions related to ESS visibility objects.
    <Object Identifier> 1.3.6.1.4.1.1206.4.2.5.127.2.8"
::= {essGroups 8}

-- This object has been deprecated.
essVisibilityGroupV1 OBJECT-GROUP
  OBJECTS {
      essVisibility }
  STATUS   deprecated
  DESCRIPTION
    "<Definition> The objects required to claim support for visibility readings for v01.
    <Superseded by> essVisibilityDataGroupV5
    <Object Identifier> 1.3.6.1.4.1.1206.4.2.5.127.2.8.1"
::= {essVisibilityGroups 1}

essVisibilitySituationGroupV1 OBJECT-GROUP
  OBJECTS {
      essVisibilitySituation }
  STATUS   current
  DESCRIPTION
    "<Definition> The objects required to claim support for visibility situation readings for v01.
    <Object Identifier> 1.3.6.1.4.1.1206.4.2.5.127.2.8.2"
::= {essVisibilityGroups 2}

-- This object has been deprecated.
essVisibilitySensorLocationGroupV4 OBJECT-GROUP
  OBJECTS {
      visibilitySensorHeight,
      visibilitySensorLatitude,
      visibilitySensorLongitude,
      visibilitySensorLocation }
  STATUS   deprecated
  DESCRIPTION
    "<Definition> The objects required to claim support for visibility sensor location for v04.
    <Superseded by> essVisibilitySensorLocationGroupV5
    <Object Identifier> 1.3.6.1.4.1.1206.4.2.5.127.2.8.3"
::= {essVisibilityGroups 3}

-- This object has been deprecated.
essVisibilitySensorInfoGroupV4 OBJECT-GROUP
  OBJECTS {
      visibilitySensorModelInformation }
  STATUS   deprecated
  DESCRIPTION
    "<Definition> The objects required to claim support for visibility sensor identification for v04.
    <Superseded by> essVisibilitySensorInfoGroupV5
    <Object Identifier> 1.3.6.1.4.1.1206.4.2.5.127.2.8.4"
::= {essVisibilityGroups 4}

essVisibilityDataGroupV5 OBJECT-GROUP
  OBJECTS {
      essNumVisibilitySensors,
      essVisibilitySensorCurrentReading }
  STATUS   current
  DESCRIPTION
    "<Definition> The objects required to claim support for visibility readings for v05.
    <Object Identifier> 1.3.6.1.4.1.1206.4.2.5.127.2.8.5"
::= {essVisibilityGroups 5}

essCloudSituationGroupV5 OBJECT-GROUP
  OBJECTS {
      essCloudSituationV4 }
  STATUS   current
  DESCRIPTION
    "<Definition> The objects required to claim support for cloud situation readings for v05.
    <Object Identifier> 1.3.6.1.4.1.1206.4.2.5.127.2.8.6"
::= {essVisibilityGroups 6}

essVisibilitySensorLocationGroupV5 OBJECT-GROUP
  OBJECTS {
      essVisibilitySensorLocation,
      essVisibilitySensorXOffset,
      essVisibilitySensorYOffset,
      essVisibilitySensorZOffset,
      essVisibilitySensorDirection }
  STATUS   current
  DESCRIPTION
    "<Definition> The objects required to claim support for visibility sensor location for v05.
    <Object Identifier> 1.3.6.1.4.1.1206.4.2.5.127.2.8.7"
::= {essVisibilityGroups 7}

essVisibilitySensorInfoGroupV5 OBJECT-GROUP
  OBJECTS {
      essVisibilitySensorEntityID }
  STATUS   current
  DESCRIPTION
    "<Definition> The objects required to claim support for visibility sensor identification for v05.
    <Object Identifier> 1.3.6.1.4.1.1206.4.2.5.127.2.8.8"
::= {essVisibilityGroups 8}

-- 5.17.9 Pavement Groups
essPavementGroups OBJECT-IDENTITY
    STATUS       current
  DESCRIPTION
    "<Definition> A node for group definitions related to ESS objects.
    <Object Identifier> 1.3.6.1.4.1.1206.4.2.5.127.2.9"
::= {essGroups 9}

essPavementSensorCountGroupV1 OBJECT-GROUP
  OBJECTS {
      numEssPavementSensors,
      essPavementSensorIndex }
  STATUS   current
  DESCRIPTION
    "<Definition> The objects required to identify the number of pavement sensors are available for v01.
    <Object Identifier> 1.3.6.1.4.1.1206.4.2.5.127.2.9.1"
::= {essPavementGroups 1}

essPavementSensorMetaDataGroupV1 OBJECT-GROUP
  OBJECTS {
      essPavementSensorLocation,
      essPavementType,
      essPavementExposure,
      essPavementSensorType }
  STATUS   current
  DESCRIPTION
    "<Definition> The objects required to claim support for pavement sensor meta-data for v01.
    <Object Identifier> 1.3.6.1.4.1.1206.4.2.5.127.2.9.2"
::= {essPavementGroups 2}

-- This object has been deprecated.
essPavementSensorSurfaceStatusGroupV1 OBJECT-GROUP
  OBJECTS {
      essSurfaceStatus }
  STATUS   deprecated
  DESCRIPTION
    "<Definition> The objects required to claim support for pavement sensor condition for v01.
    <Superseded by> essPavementSurfaceCondGroupV4
    <Object Identifier> 1.3.6.1.4.1.1206.4.2.5.127.2.9.3"
::= {essPavementGroups 3}

-- This object has been deprecated.
essPavementSensorElevationGroupV1 OBJECT-GROUP
  OBJECTS {
      essPavementElevation }
  STATUS   deprecated
  DESCRIPTION
    "<Definition> The objects required to claim support for pavement sensor elevation data for v01.
    <Superseded by> essPavementSensorLocationGroupV5
    <Object Identifier> 1.3.6.1.4.1.1206.4.2.5.127.2.9.4"
::= {essPavementGroups 4}

essPavementSurfaceTempGroupV1 OBJECT-GROUP
  OBJECTS {
      essSurfaceTemperature,
      essPavementSensorError }
  STATUS   current
  DESCRIPTION
    "<Definition> The objects required to claim support for pavement surface readings for v01.
    <Object Identifier> 1.3.6.1.4.1.1206.4.2.5.127.2.9.5"
::= {essPavementGroups 5}

-- This object has been deprecated.
essPavementEnhancedGroupV1 OBJECT-GROUP
  OBJECTS {
      essPavementTemperature,
      essSurfaceWaterDepth }
  STATUS   deprecated
  DESCRIPTION
    "<Definition> The objects required to claim support for enhanced pavement readings for v01.
    <Superseded by> essPavementTemperatureGroupV2
    <Object Identifier> 1.3.6.1.4.1.1206.4.2.5.127.2.9.6"
::= {essPavementGroups 6}

-- This object has been deprecated.
essSurfaceConductivityGroupV1 OBJECT-GROUP
  OBJECTS {
      essSurfaceConductivity }
  STATUS   deprecated
  DESCRIPTION
    "<Definition> The objects required to claim support for pavement surface conductivity for v01.
    <Superseded by> essSurfaceConductivityGroupV2
    <Object Identifier> 1.3.6.1.4.1.1206.4.2.5.127.2.9.7"
::= {essPavementGroups 7}

essSurfaceSalinityGroupV1 OBJECT-GROUP
  OBJECTS {
      essSurfaceSalinity }
  STATUS   current
  DESCRIPTION
    "<Definition> The objects required to claim support for pavement salinity for v01.
    <Object Identifier> 1.3.6.1.4.1.1206.4.2.5.127.2.9.8"
::= {essPavementGroups 8}

essPavementFreezeGroupV1 OBJECT-GROUP
  OBJECTS {
      essSurfaceFreezePoint,
      essSurfaceBlackIceSignal }
  STATUS   current
  DESCRIPTION
    "<Definition> The objects required to claim support for pavement surface freeze readings for v01.
    <Superseded by> essPavementTemperatureGroupV2
    <Object Identifier> 1.3.6.1.4.1.1206.4.2.5.127.2.9.9"
::= {essPavementGroups 9}

essSurfaceConductivityGroupV2 OBJECT-GROUP
  OBJECTS {
      essSurfaceConductivityV2 }
  STATUS   current
  DESCRIPTION
    "<Definition> The objects required to claim support for pavement surface conductivity for v02.
    <Object Identifier> 1.3.6.1.4.1.1206.4.2.5.127.2.9.10"
::= {essPavementGroups 10}

essPavementTemperatureGroupV2 OBJECT-GROUP
  OBJECTS {
      essPavementTemperature,
      essSurfaceIceOrWaterDepth }
  STATUS   current
  DESCRIPTION
    "<Definition> The objects required to claim support for pavement temperature readings for v02.
    <Object Identifier> 1.3.6.1.4.1.1206.4.2.5.127.2.9.11"
::= {essPavementGroups 11}

-- This object has been deprecated.
essPavementBlockGroupV2 OBJECT-GROUP
  OBJECTS {
      essPavementBlock }
  STATUS   deprecated
  DESCRIPTION
    "<Definition> The objects required to claim support for the pavement block in v02.
    <Superseded by> essPavementBlockGroupV3
    <Object Identifier> 1.3.6.1.4.1.1206.4.2.5.127.2.9.12"
::= {essPavementGroups 12}

essPavementSensorDepthGroupV2 OBJECT-GROUP
  OBJECTS {
      pavementSensorTemperatureDepth }
  STATUS   current
  DESCRIPTION
    "<Definition> The objects required to claim support for the pavement sensor depth in v02.
    <Object Identifier> 1.3.6.1.4.1.1206.4.2.5.127.2.9.13"
::= {essPavementGroups 13}

-- This object has been deprecated.
essPavementSensorInfoGroupV2 OBJECT-GROUP
  OBJECTS {
      pavementSensorModelInformation }
  STATUS   deprecated
  DESCRIPTION
    "<Definition> The objects required to claim support for pavement sensor identification for v02.
    <Superseded by> essPavementSensorInfoGroupV5
    <Object Identifier> 1.3.6.1.4.1.1206.4.2.5.127.2.9.14"
::= {essPavementGroups 14}

-- This object has been deprecated.
essPavementBlockGroupV3 OBJECT-GROUP
  OBJECTS {
      essPavementV3Block }
  STATUS   deprecated
  DESCRIPTION
    "<Definition> The objects required to claim support for the pavement block in v03.
    <Withdrawn> In v04
    <Object Identifier> 1.3.6.1.4.1.1206.4.2.5.127.2.9.15"
::= {essPavementGroups 15}

essPavementSurfaceCondGroupV4 OBJECT-GROUP
  OBJECTS {
      pavementSensorSurfaceCondition }
  STATUS   current
  DESCRIPTION
    "<Definition> The objects required to claim support for pavement surface condition readings for v04.
    <Object Identifier> 1.3.6.1.4.1.1206.4.2.5.127.2.9.16"
::= {essPavementGroups 16}

essPavementFrictionGroupV4 OBJECT-GROUP
  OBJECTS {
      pavementSensorFrictionCoefficient }
  STATUS   current
  DESCRIPTION
    "<Definition> The objects required to claim support for pavement friction readings for v04.
    <Object Identifier> 1.3.6.1.4.1.1206.4.2.5.127.2.9.17"
::= {essPavementGroups 17}

essPavementIcePercentGroupV4 OBJECT-GROUP
  OBJECTS {
      pavementIcePercentage }
  STATUS   current
  DESCRIPTION
    "<Definition> The objects required to claim support for monitoring pavement ice percentage for v04.
    <Object Identifier> 1.3.6.1.4.1.1206.4.2.5.127.2.9.18"
::= {essPavementGroups 18}

-- This object has been deprecated.
essPavementSensorLocationGroupV4 OBJECT-GROUP
  OBJECTS {
      essPavementSensorLocation,
      pavementSensorLatitude,
      pavementSensorLongitude,
      pavementMonitorLatitude,
      pavementMonitorLongitude }
  STATUS   deprecated
  DESCRIPTION
    "<Definition> The objects required to claim support for pavement sensor location for v04.
    <Superseded by> essPavementSensorLocationGroupV5
    <Object Identifier> 1.3.6.1.4.1.1206.4.2.5.127.2.9.19"
::= {essPavementGroups 19}

essPavementForecastGroupV5 OBJECT-GROUP
  OBJECTS {
      pavementSensorForecastCondition }
  STATUS   current
  DESCRIPTION
    "<Definition> The objects required to claim support for pavement forecast readings for v05.
    <Object Identifier> 1.3.6.1.4.1.1206.4.2.5.127.2.9.20"
::= {essPavementGroups 20}

essPavementSensorLocationGroupV5 OBJECT-GROUP
  OBJECTS {
      essPavementSensorLocation,
      essPavementMonitorXOffset,
      essPavementMonitorYOffset,
      essPavementMonitorZOffset,
      essPavementMonitorArea,
      essPavementSensorXOffset,
      essPavementSensorYOffset }
  STATUS   current
  DESCRIPTION
    "<Definition> The objects required to claim support for pavement sensor location for v05.
    <Object Identifier> 1.3.6.1.4.1.1206.4.2.5.127.2.9.21"
::= {essPavementGroups 21}

essPavementSensorInfoGroupV5 OBJECT-GROUP
  OBJECTS {
      essPavementSensorEntityID }
  STATUS   current
  DESCRIPTION
    "<Definition> The objects required to claim support for pavement sensor identification for v05.
    <Object Identifier> 1.3.6.1.4.1.1206.4.2.5.127.2.9.22"
::= {essPavementGroups 22}

-- 5.17.10 Subsurface Groups
essSubSurfaceGroups OBJECT-IDENTITY
    STATUS       current
  DESCRIPTION
    "<Definition> A node for group definitions related to ESS subsurface objects.
    <Object Identifier> 1.3.6.1.4.1.1206.4.2.5.127.2.10"
::= {essGroups 10}

essSubSurfaceSensorCountGroupGroupV1 OBJECT-GROUP
  OBJECTS {
      numEssSubSurfaceSensors,
      essSubSurfaceSensorIndex }
  STATUS   current
  DESCRIPTION
    "<Definition> The objects required to identify the number of subsurface sensors are available for v01.
    <Object Identifier> 1.3.6.1.4.1.1206.4.2.5.127.2.10.1"
::= {essSubSurfaceGroups 1}

essSubSurfaceMoistureGroupV1 OBJECT-GROUP
  OBJECTS {
      essSubSurfaceMoisture }
  STATUS   current
  DESCRIPTION
    "<Definition> The objects required to claim support for subsurface moisture readings for v01.
    <Object Identifier> 1.3.6.1.4.1.1206.4.2.5.127.2.10.2"
::= {essSubSurfaceGroups 2}

-- This object has been deprecated.
essSubSurfaceBlockGroupV2 OBJECT-GROUP
  OBJECTS {
      essSubSurfaceBlock }
  STATUS   deprecated
  DESCRIPTION
    "<Definition> The objects required to claim support for the subsurface block in v02.
    <Withdrawn> In v04
    <Object Identifier> 1.3.6.1.4.1.1206.4.2.5.127.2.10.3"
::= {essSubSurfaceGroups 3}

-- This object has been deprecated.
essSubSurfaceSensorLocationGroupV4 OBJECT-GROUP
  OBJECTS {
      essSubSurfaceSensorLatitude,
      essSubSurfaceSensorLongitude }
  STATUS   deprecated
  DESCRIPTION
    "<Definition> The objects required to claim support for subsurface sensor location for v04.
    <Superseded by> essSubSurfaceSensorLocationGroupV5
    <Object Identifier> 1.3.6.1.4.1.1206.4.2.5.127.2.10.4"
::= {essSubSurfaceGroups 4}

-- This object has been deprecated.
essSubSurfaceSensorInfoGroupV4 OBJECT-GROUP
  OBJECTS {
      essSubSurfaceSensorModelInformation }
  STATUS   deprecated
  DESCRIPTION
    "<Definition> The objects required to claim support for subsurface sensor identification for v04.
    <Superseded by> essSubSurfaceSensorInfoGroupV5
    <Object Identifier> 1.3.6.1.4.1.1206.4.2.5.127.2.10.5"
::= {essSubSurfaceGroups 5}

essSubSurfaceDataGroupV5 OBJECT-GROUP
  OBJECTS {
      essSubSurfaceTemperature,
      essSubSurfaceSensorError }
  STATUS   current
  DESCRIPTION
    "<Definition> The objects required to claim support for subsurface data readings for v05.
    <Object Identifier> 1.3.6.1.4.1.1206.4.2.5.127.2.10.6"
::= {essSubSurfaceGroups 6}

essSubSurfaceSensorMetaDataGroupV5 OBJECT-GROUP
  OBJECTS {
      essSubSurfaceSensorLocation,
      essSubSurfaceType,
      essSubSurfaceSensorDepth }
  STATUS   current
  DESCRIPTION
    "<Definition> The objects required to claim support for subsurface sensor meta-data for v05.
    <Object Identifier> 1.3.6.1.4.1.1206.4.2.5.127.2.10.7"
::= {essSubSurfaceGroups 7}

essSubSurfaceSensorLocationGroupV5 OBJECT-GROUP
  OBJECTS {
      essSubSurfaceSensorXOffset,
      essSubSurfaceSensorYOffset }
  STATUS   current
  DESCRIPTION
    "<Definition> The objects required to claim support for subsurface sensor location for v05.
    <Object Identifier> 1.3.6.1.4.1.1206.4.2.5.127.2.10.8"
::= {essSubSurfaceGroups 8}

essSubSurfaceSensorInfoGroupV5 OBJECT-GROUP
  OBJECTS {
      essSubSurfaceSensorEntityID }
  STATUS   current
  DESCRIPTION
    "<Definition> The objects required to claim support for subsurface sensor identification for v05.
    <Object Identifier> 1.3.6.1.4.1.1206.4.2.5.127.2.10.9"
::= {essSubSurfaceGroups 9}

-- 5.17.11 Snapshot Groups
essSnapshotGroups OBJECT-IDENTITY
    STATUS       current
  DESCRIPTION
    "<Definition> A node for group definitions related to ESS snapshot objects.
    <Object Identifier> 1.3.6.1.4.1.1206.4.2.5.127.2.11"
::= {essGroups 11}

essSnapshotCameraGroupV2 OBJECT-GROUP
  OBJECTS {
      essSnapshotNumberOfCameras,
      essSnapshotCameraIndex,
      essSnapshotCameraDescription,
      essSnapshotCameraStoragePath,
      essSnapshotCameraCommand,
      essSnapshotCameraError }
  STATUS   current
  DESCRIPTION
    "<Definition> The objects required to claim support for snapshots for v02.
    <Object Identifier> 1.3.6.1.4.1.1206.4.2.5.127.2.11.1"
::= {essSnapshotGroups 1}

-- This object has been deprecated.
essSnapshotFilenameGroupV3 OBJECT-GROUP
  OBJECTS {
      essSnapshotCameraFilename }
  STATUS   deprecated
  DESCRIPTION
    "<Definition> The objects required to claim support for snapshots for v03.
    <Superseded by> essSnapshotFilenameGroupV5
    <Object Identifier> 1.3.6.1.4.1.1206.4.2.5.127.2.11.2"
::= {essSnapshotGroups 2}

essSnapshotFilenameGroupV5 OBJECT-GROUP
  OBJECTS {
      essSnapshotCameraSupportedFormats,
      essSnapshotCameraFileFormat,
      essSnapshotCameraFilenameV5 }
  STATUS   current
  DESCRIPTION
    "<Definition> The objects required to claim support for snapshots for v05.
    <Object Identifier> 1.3.6.1.4.1.1206.4.2.5.127.2.11.3"
::= {essSnapshotGroups 3}

essSnapshotCameraInfoGroupV5 OBJECT-GROUP
  OBJECTS {
      essSnapshotCameraEntityID }
  STATUS   current
  DESCRIPTION
    "<Definition> The objects required to claim support for snapshot camera identification for v05.
    <Object Identifier> 1.3.6.1.4.1.1206.4.2.5.127.2.11.4"
::= {essSnapshotGroups 4}

-- 5.17.12 Observed Groups
essObservedGroups OBJECT-IDENTITY
    STATUS       current
  DESCRIPTION
    "<Definition> A node for group definitions related to ESS observed readings.
    <Object Identifier> 1.3.6.1.4.1.1206.4.2.5.127.2.12"
::= {essGroups 12}

-- This object has been deprecated.
essObservedReadingGroupV1 OBJECT-GROUP
  OBJECTS {
      essWindSituation,
      essPrecipSituation,
      essCloudSituation,
      essVisibilitySituation }
  STATUS   deprecated
  DESCRIPTION
    "<Definition> The objects required to claim support for observed readings for v01.
    <Superseded by> essObservedReadingGroupV4
    <Object Identifier> 1.3.6.1.4.1.1206.4.2.5.127.2.12.1"
::= {essObservedGroups 1}

-- This object has been deprecated.
essMobileObservationGroupV1 OBJECT-GROUP
  OBJECTS {
      essMobileObservationGroundState,
      essMobileObservationPavement }
  STATUS   deprecated
  DESCRIPTION
    "<Definition> The objects required to claim support for mobile observed readings for v01.
    <Superseded by> essObservedGroundStateGroupV4 and essObservedPavementStateGroupV4
    <Object Identifier> 1.3.6.1.4.1.1206.4.2.5.127.2.12.2"
::= {essObservedGroups 2}

essObservedReadingGroupV4 OBJECT-GROUP
  OBJECTS {
      essWindSituation,
      essPrecipSituation,
      essCloudSituationV4,
      essVisibilitySituation }
  STATUS   current
  DESCRIPTION
    "<Definition> The objects required to claim support for observed readings for v04. 
    <Object Identifier> 1.3.6.1.4.1.1206.4.2.5.127.2.12.3"
::= {essObservedGroups 3}

essObservedGroundStateGroupV4 OBJECT-GROUP
  OBJECTS {
      essMobileObservationGroundStateV4 }
  STATUS   current
  DESCRIPTION
    "<Definition> The objects required to claim support for observed ground state readings for v04.
    <Object Identifier> 1.3.6.1.4.1.1206.4.2.5.127.2.12.4"
::= {essObservedGroups 4}

essObservedPavementStateGroupV4 OBJECT-GROUP
  OBJECTS {
      essMobileObservationPavementV4 }
  STATUS   current
  DESCRIPTION
    "<Definition> The objects required to claim support for observed pavement state readings for v04.
    <Object Identifier> 1.3.6.1.4.1.1206.4.2.5.127.2.12.5"
::= {essObservedGroups 5}

-- 5.17.13 Water Level Groups
essWaterLevelGroups OBJECT-IDENTITY
    STATUS       current
  DESCRIPTION
    "<Definition> A node for group definitions related to ESS water level objects.
    <Object Identifier> 1.3.6.1.4.1.1206.4.2.5.127.2.13"
::= {essGroups 13}

-- This object has been deprecated.
essWaterDepthGroupV1 OBJECT-GROUP
  OBJECTS {
      essWaterDepth }
  STATUS   deprecated
  DESCRIPTION
    "<Definition> The objects required to claim support for water depth readings for v01.
    <Superseded by> essWaterLevelDataGroupV2
    <Object Identifier> 1.3.6.1.4.1.1206.4.2.5.127.2.13.1"
::= {essWaterLevelGroups 1}

essWaterLevelDataGroupV2 OBJECT-GROUP
  OBJECTS {
      waterLevelSensorTableNumSensors,
      waterLevelSensorIndex,
      waterLevelSensorReading }
  STATUS   current
  DESCRIPTION
    "<Definition> The objects required to claim support for water level readings for v02.
    <Object Identifier> 1.3.6.1.4.1.1206.4.2.5.127.2.13.2"
::= {essWaterLevelGroups 2}

essWaterLevelSensorConfigurationGroupV4 OBJECT-GROUP
  OBJECTS {
      waterLevelSensorWarningLevel }
  STATUS   current
  DESCRIPTION
    "<Definition> The objects required to claim support for water level configuration for v04.
    <Object Identifier> 1.3.6.1.4.1.1206.4.2.5.127.2.13.3"
::= {essWaterLevelGroups 3}

-- This object has been deprecated.
essWaterLevelSensorLocationGroupV4 OBJECT-GROUP
  OBJECTS {
      waterLevelSensorHeight,
      waterLevelSensorLatitude,
      waterLevelSensorLongitude,
      waterLevelSensorLocation,
      waterLevelSensorReferencePoint }
  STATUS   deprecated
  DESCRIPTION
    "<Definition> The objects required to claim support for water level sensor location for v04.
    <Superseded by> essWaterLevelSensorLocationGroupV5
    <Object Identifier> 1.3.6.1.4.1.1206.4.2.5.127.2.13.4"
::= {essWaterLevelGroups 4}

-- This object has been deprecated.
essWaterLevelSensorInfoGroupV4 OBJECT-GROUP
  OBJECTS {
      waterLevelSensorModelInformation }
  STATUS   deprecated
  DESCRIPTION
    "<Definition> The objects required to claim support for water level sensor identification for v04.
    <Superseded by> essWaterLevelSensorInfoGroupV5
    <Object Identifier> 1.3.6.1.4.1.1206.4.2.5.127.2.13.5"
::= {essWaterLevelGroups 5}

essWaterLevelSensorLocationGroupV5 OBJECT-GROUP
  OBJECTS {
      waterLevelSensorLocation,
      waterLevelSensorReferencePoint,
      waterLevelSensorXOffset,
      waterLevelSensorYOffset,
      waterLevelSensorZOffset }
  STATUS   current
  DESCRIPTION
    "<Definition> The objects required to claim support for water level sensor location for v05.
    <Object Identifier> 1.3.6.1.4.1.1206.4.2.5.127.2.13.6"
::= {essWaterLevelGroups 6}

essWaterLevelSensorInfoGroupV5 OBJECT-GROUP
  OBJECTS {
      waterLevelSensorEntityID }
  STATUS   current
  DESCRIPTION
    "<Definition> The objects required to claim support for water level sensor identification for v05.
    <Object Identifier> 1.3.6.1.4.1.1206.4.2.5.127.2.13.7"
::= {essWaterLevelGroups 7}

-- 5.17.14 Air Quality Groups
essAirQualityGroups OBJECT-IDENTITY
    STATUS       current
  DESCRIPTION
    "<Definition> A node for group definitions related to ESS air quality objects.
    <Object Identifier> 1.3.6.1.4.1.1206.4.2.5.127.2.14"
::= {essGroups 14}

essAirQualityCOGroupV1 OBJECT-GROUP
  OBJECTS {
      essCO }
  STATUS   current
  DESCRIPTION
    "<Definition> The objects required to claim support for carbon monoxide readings for v01.
    <Object Identifier> 1.3.6.1.4.1.1206.4.2.5.127.2.14.1"
::= {essAirQualityGroups 1}

-- This object has been deprecated.
essAirQualityCO2GroupV1 OBJECT-GROUP
  OBJECTS {
      essCO2 }
  STATUS   deprecated
  DESCRIPTION
    "<Definition> The objects required to claim support for carbon dioxide readings for v01.
    <Superseded by> essAirQualityCO2GroupV4
    <Object Identifier> 1.3.6.1.4.1.1206.4.2.5.127.2.14.2"
::= {essAirQualityGroups 2}

-- This object has been deprecated.
essAirQualityNOGroupV1 OBJECT-GROUP
  OBJECTS {
      essNO }
  STATUS   deprecated
  DESCRIPTION
    "<Definition> The objects required to claim support for nitric oxide readings for v01.
    <Superseded by> essAirQualityNOGroupV4
    <Object Identifier> 1.3.6.1.4.1.1206.4.2.5.127.2.14.3"
::= {essAirQualityGroups 3}

essAirQualityNO2GroupV1 OBJECT-GROUP
  OBJECTS {
      essNO2 }
  STATUS   current
  DESCRIPTION
    "<Definition> The objects required to claim support for nitrogen dioxide readings for v01.
    <Object Identifier> 1.3.6.1.4.1.1206.4.2.5.127.2.14.4"
::= {essAirQualityGroups 4}

essAirQualitySO2GroupV1 OBJECT-GROUP
  OBJECTS {
      essSO2 }
  STATUS   current
  DESCRIPTION
    "<Definition> The objects required to claim support for sulfur dioxide readings for v01.
    <Object Identifier> 1.3.6.1.4.1.1206.4.2.5.127.2.14.5"
::= {essAirQualityGroups 5}

-- This object has been deprecated.
essAirQualityO3GroupV1 OBJECT-GROUP
  OBJECTS {
      essO3 }
  STATUS   deprecated
  DESCRIPTION
    "<Definition> The objects required to claim support for ozone readings for v01.
    <Superseded by> essAirQualityO3GroupV4
    <Object Identifier> 1.3.6.1.4.1.1206.4.2.5.127.2.14.6"
::= {essAirQualityGroups 6}

essAirQualityPM10GroupV1 OBJECT-GROUP
  OBJECTS {
      essPM10 }
  STATUS   current
  DESCRIPTION
    "<Definition> The objects required to claim support for small (10 micrometer) particulate matter readings for v01.
    <Object Identifier> 1.3.6.1.4.1.1206.4.2.5.127.2.14.7"
::= {essAirQualityGroups 7}

-- This object has been deprecated.
essAQBlockGroupV2 OBJECT-GROUP
  OBJECTS {
      essAirQualityBlock }
  STATUS   deprecated
  DESCRIPTION
    "<Definition> The objects required to claim support for the air quality block in v02.
    <Withdrawn> In v04
    <Object Identifier> 1.3.6.1.4.1.1206.4.2.5.127.2.14.8"
::= {essAirQualityGroups 8}

essAirQualityCO2GroupV4 OBJECT-GROUP
  OBJECTS {
      essCO2V4 }
  STATUS   current
  DESCRIPTION
    "<Definition> The objects required to claim support for carbon dioxide readings for v04.
    <Object Identifier> 1.3.6.1.4.1.1206.4.2.5.127.2.14.9"
::= {essAirQualityGroups 9}

essAirQualityNOGroupV4 OBJECT-GROUP
  OBJECTS {
      essNOV4 }
  STATUS   current
  DESCRIPTION
    "<Definition> The objects required to claim support for nitric oxide readings for v04.
    <Object Identifier> 1.3.6.1.4.1.1206.4.2.5.127.2.14.10"
::= {essAirQualityGroups 10}

essAirQualityO3GroupV4 OBJECT-GROUP
  OBJECTS {
      essO3V4 }
  STATUS   current
  DESCRIPTION
    "<Definition> The objects required to claim support for ozone readings for v04.
    <Object Identifier> 1.3.6.1.4.1.1206.4.2.5.127.2.14.11"
::= {essAirQualityGroups 11}

essAirQualityPM25GroupV4 OBJECT-GROUP
  OBJECTS {
      essPM25 }
  STATUS   current
  DESCRIPTION
    "<Definition> The objects required to claim support for small (2.5 micrometer) particulate matter readings for v04.
    <Object Identifier> 1.3.6.1.4.1.1206.4.2.5.127.2.14.12"
::= {essAirQualityGroups 12}

-- This object has been deprecated.
essAirQualitySensorLocationGroupV4 OBJECT-GROUP
  OBJECTS {
      airQualitySensorTableNumSensors,
      airQualitySensorIndex,
      airQualitySensorHeight,
      airQualitySensorLatitude,
      airQualitySensorLongitude,
      airQualitySensorLocation }
  STATUS   deprecated
  DESCRIPTION
    "<Definition> The objects required to claim support for air quality sensor location for v04.
    <Superseded by> essAirQualitySensorLocationGroupV5
    <Object Identifier> 1.3.6.1.4.1.1206.4.2.5.127.2.14.13"
::= {essAirQualityGroups 13}

-- This object has been deprecated.
essAirQualitySensorInfoGroupV4 OBJECT-GROUP
  OBJECTS {
      airQualitySensorModelInformation }
  STATUS   deprecated
  DESCRIPTION
    "<Definition> The objects required to claim support for air quality sensor identification for v04. 
    <Superseded by> essAirQualitySensorInfoGroupV5
    <Object Identifier> 1.3.6.1.4.1.1206.4.2.5.127.2.14.14"
::= {essAirQualityGroups 14}

essAirQualityPM1GroupV5 OBJECT-GROUP
  OBJECTS {
      essPM1 }
  STATUS   current
  DESCRIPTION
    "<Definition> The objects required to claim support for small (1.0 micrometer) particulate matter readings for v05.
    <Object Identifier> 1.3.6.1.4.1.1206.4.2.5.127.2.14.15"
::= {essAirQualityGroups 15}

essAirQualitySensorLocationGroupV5 OBJECT-GROUP
  OBJECTS {
      airQualitySensorTableNumSensors,
      airQualitySensorIndex,
      airQualitySensorLocation,
      airQualitySensorXOffset,
      airQualitySensorYOffset,
      airQualitySensorZOffset }
  STATUS   current
  DESCRIPTION
    "<Definition> The objects required to claim support for air quality sensor location for v05.
    <Object Identifier> 1.3.6.1.4.1.1206.4.2.5.127.2.14.16"
::= {essAirQualityGroups 16}

essAirQualitySensorInfoGroupV5 OBJECT-GROUP
  OBJECTS {
      airQualitySensorEntityID }
  STATUS   current
  DESCRIPTION
    "<Definition> The objects required to claim support for air quality sensor identification for v05. 
    <Object Identifier> 1.3.6.1.4.1.1206.4.2.5.127.2.14.17"
::= {essAirQualityGroups 17}

-- 5.17.15 Pavement Treatment Groups
essPavementTreatmentGroups OBJECT-IDENTITY
    STATUS       current
  DESCRIPTION
    "<Definition> A node for group definitions related to PTS objects.
    <Object Identifier> 1.3.6.1.4.1.1206.4.2.5.127.2.15"
::= {essGroups 15}

ptsProductGroupV1 OBJECT-GROUP
  OBJECTS {
      numEssTreatments,
      essPavementTreatmentIndex,
      essPaveTreatProductType,
      essPaveTreatProductForm,
      essPercentProductMix }
  STATUS   current
  DESCRIPTION
    "<Definition> The objects required to claim support for pavement treatment table for v01. 
    <Object Identifier> 1.3.6.1.4.1.1206.4.2.5.127.2.15.1"
::= {essPavementTreatmentGroups 1}

ptsSpreadConfigGroupV1 OBJECT-GROUP
  OBJECTS {
      essPaveTreatmentAmount,
      essPaveTreatmentWidth }
  STATUS   current
  DESCRIPTION
    "<Definition> The objects required to claim support for pavement treatment spread configuration details for v01.
    <Object Identifier> 1.3.6.1.4.1.1206.4.2.5.127.2.15.2"
::= {essPavementTreatmentGroups 2}

-- This object has been deprecated.
ptsStatusGroupV2 OBJECT-GROUP
  OBJECTS {
      ptsSprayerState,
      ptsSignalEventCount,
      ptsLastSignalEvent,
      ptsActiveEventCount,
      ptsInactiveEventCount,
      ptsLastActiveEvent,
      ptsLastInactiveEvent,
      ptsError }
  STATUS   deprecated
  DESCRIPTION
    "<Definition> The objects required to claim support for pavement treatment status for v02.
    <Superseded by> ptsStatusGroupV5
    <Object Identifier> 1.3.6.1.4.1.1206.4.2.5.127.2.15.3"
::= {essPavementTreatmentGroups 3}

ptsConfigurationGroupV2 OBJECT-GROUP
  OBJECTS {
      ptsSignalDuration,
      ptsMonitoringDetectors }
  STATUS   current
  DESCRIPTION
    "<Definition> The objects required to claim support for pavement treatment configuration for v02.
    <Object Identifier> 1.3.6.1.4.1.1206.4.2.5.127.2.15.4"
::= {essPavementTreatmentGroups 4}

-- This object is obsolete.
ptsCommandGroupV2 OBJECT-GROUP
  OBJECTS {
      ptsOperationalMode,
      ptsCommandState }
  STATUS   obsolete
  DESCRIPTION
    "<Definition> The objects required to claim support for the pavement treatment command objects for v02.
    <Superseded by> ptsOperationGroupV3 and ptsCommandGroupV3
    <Informative> Made obsolete in v03.
    <Object Identifier> 1.3.6.1.4.1.1206.4.2.5.127.2.15.5"
::= {essPavementTreatmentGroups 5}

-- This object has been deprecated.
essPtsBlockGroupV2 OBJECT-GROUP
  OBJECTS {
      pavementTreatmentBlock }
  STATUS   deprecated
  DESCRIPTION
    "<Definition> The objects required to claim support for the pavement treatment block in v02.
    <Withdrawn> In v04
    <Object Identifier> 1.3.6.1.4.1.1206.4.2.5.127.2.15.6"
::= {essPavementTreatmentGroups 6}

ptsOperationGroupV3 OBJECT-GROUP
  OBJECTS {
      ptsOperationalModeV3 }
  STATUS   current
  DESCRIPTION
    "<Definition> The objects required to claim support for the pavement treatment operation parameter for v03.
    <Object Identifier> 1.3.6.1.4.1.1206.4.2.5.127.2.15.7"
::= {essPavementTreatmentGroups 7}

ptsCommandGroupV3 OBJECT-GROUP
  OBJECTS {
      ptsCommandStateV3 }
  STATUS   current
  DESCRIPTION
    "<Definition> The objects required to claim support for pavement treatment commands for v03.
    <Object Identifier> 1.3.6.1.4.1.1206.4.2.5.127.2.15.8"
::= {essPavementTreatmentGroups 8}

-- This object has been deprecated.
ptsLocationGroupV4 OBJECT-GROUP
  OBJECTS {
      essPavementTreatmentLatitude,
      essPavementTreatmentLongitude,
      essPavementTreatmentLocation }
  STATUS   deprecated
  DESCRIPTION
    "<Definition> The objects required to claim support for pavement treatment location for v04.
    <Superseded by> ptsLocationGroupV5
    <Object Identifier> 1.3.6.1.4.1.1206.4.2.5.127.2.15.9"
::= {essPavementTreatmentGroups 9}

-- This object has been deprecated.
ptsInfoGroupV4 OBJECT-GROUP
  OBJECTS {
      essPavementTreatmentModelInformation }
  STATUS   deprecated
  DESCRIPTION
    "<Definition> The objects required to claim support for pavement treatment system identification for v04.
    <Superseded by> ptsInfoGroupV5
    <Object Identifier> 1.3.6.1.4.1.1206.4.2.5.127.2.15.10"
::= {essPavementTreatmentGroups 10}

ptsStatusGroupV5 OBJECT-GROUP
  OBJECTS {
      ptsSprayerState,
      ptsSignalEventCount,
      ptsActiveEventCount,
      ptsInactiveEventCount,
      ptsError,
      ptsLastSignalEventTime,
      ptsLastActiveEventTime,
      ptsLastInactiveEventTime }
  STATUS   current
  DESCRIPTION
    "<Definition> The objects required to claim support for pavement treatment status for v05. 
    <Object Identifier> 1.3.6.1.4.1.1206.4.2.5.127.2.15.11"
::= {essPavementTreatmentGroups 11}

ptsLocationGroupV5 OBJECT-GROUP
  OBJECTS {
      essPavementTreatmentLocation,
      ptsXOffset,
      ptsYOffset }
  STATUS   current
  DESCRIPTION
    "<Definition> The objects required to claim support for pavement treatment location for v05.
    <Object Identifier> 1.3.6.1.4.1.1206.4.2.5.127.2.15.12"
::= {essPavementTreatmentGroups 12}

ptsInfoGroupV5 OBJECT-GROUP
  OBJECTS {
      ptsEntityID }
  STATUS   current
  DESCRIPTION
    "<Definition> The objects required to claim support for pavement treatment system identification for v05.
    <Object Identifier> 1.3.6.1.4.1.1206.4.2.5.127.2.15.13"
::= {essPavementTreatmentGroups 13}

END
